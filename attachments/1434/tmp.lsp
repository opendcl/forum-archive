(DCL_PROJECT_LOAD "Revisiones" T)


(defun c:Revisiones_pltRevisiones_OnInicializar (/)
  
(DCL_GRID_ADDCOLUMNS
  Revisiones_pltRevisiones_grdDatos
  '(("1")("2")("3")("4"))
  
)

(DCL_GRID_FILLLIST
  Revisiones_pltRevisiones_grdDatos
  '(("StrPrueba" "StrPrueba" "StrPrueba" "StrPrueba")
    ("StrPrueba" "StrPrueba" "StrPrueba" "StrPrueba")
   )
)

(DCL_GRID_SETCELLSTYLE
  Revisiones_pltRevisiones_grdDatos   0 0 18
 )

(DCL_GRID_SETCELLSTYLE
  Revisiones_pltRevisiones_grdDatos   0 1 18
 )
)

(DCL_FORM_SHOW Revisiones_pltRevisiones)

 ;|«Visual LISP© Format Options»
(80 2 40 2 nil "end of " 60 9 2 0 0 T T T T)
;*** DO NOT add text below the comment! ***|;
