;;;===========================================================================
;;;
;;; estbk.lsp
;;;
;;; Klinton Verde
;;; Realizado => Enero del 2012
;;;
;;;===========================================================================
;;;
;;; Estandarizar bloques para la corporacion Volcan; trabaja con OPENDCL
;;;
;;;===========================================================================

;;(arxload "C:\\Program Files (x86)\\Common Files\\OpenDCL\\OpenDCL.x64.18.arx")
(vl-load-com)
(defun CUASTA ()
'("YWt6A2aXAAA99aLWBuKTAns+a7WJgZZNbk8/kjx7kjjhsQQcySbe3uw0NPf6NHWso1vzSqyjdlZb"
"o19X39pWtIGSIPoF6W4CwIkDoaGBBUKJzM3FjefnLQ0YCMMNhMGL3f+xKgBa+9pvcWw47W48J61v"
"5H8BzzUVh6+RFmWk+8afTEFiEzgFrzCGuXU5xZ4FUWz+XRCGoPiIvq9Iyn2T+ESCLpw/Ag4DUSBx"
"EdRhPaJ7KXueUBDGvHWpSL1JSSC8bsm9QWycCGIBTaK3fDlCBuVC/sppNHz+QGGzuj7PYC0dwyP2"
"1ljftxb+nqyynZZA7Drcln9sf0I3Wnabk/aUaypj3v+l16auajo4KvRGUjBzrhXUhz2b7S75VBrW"
"8qFhOlZ5bbT/+gyhLgWme1RzSoMFJ35V0d9mdqNPIkGiNnJ6NGT2QoAJa0R8PcXxWh725nDXLFeU"
"X1SY3winn/aUVeSIwyeCxHM7B1NRpPn4Ep9IZCf+ya97lndVoGEy/9oV0g5ad4HOHVRnPEWPFlSn"
"Dm8rV5+EPTwHpFq0jGm8Cye0TBB2JnUNzi019/hOk2KgVSCWg9CfA29nqnvXUjJW9XC0DixZGHWJ"
"d6n7dptvshVM3IQA9JR851cfmxfqSAVvkVRJduNhql53I+h82y4vbXI48tyoCjJnXN5gYCI3mpgE"
"eS2F/N9MqG/U9T2b9aaLNT2bKaaLCz0bedICANaS8KMB+B6wGXebDfqMFzxnM9xic68S53bdW00d"
"M4aelLiQvoMAZS+jzfD+qtoveeaZd+45a8bqXtCC7wPhIkcaAIF/rUvnzPpZcy1okxuihId/4mmJ"
"c8/vw6zxbiOCd73l5gy9+YSq/IsPlN5D7a636rHy67N2lhq4zn4vZH1VSDi13yb6nVNjVI1fNB0H"
"9euhbeo5GEI/9qwG8gH7jzK+JrrPTHM70qZCoGZJxG/vnKHhaiSZ/cEqLXcvteluy8J3G2E8p5V5"
"L40pOVQTPAVT/exb68Fzo/E1yOsuwQeuTDaby/qEEz2Dv8AOybuQ3r80JfYQRZ1mtiUOvhXaj3oe"
"fJD0Ma0tdtA+YBX5xZGCjd5KL6LThr8Xh44RYHSpo4kJRVHnzbC7FBFa8h5/n4Q7vPa24k9185Py"
"YW7bTcyBvbBW9fhHnYEiGEJQ/ZucTc+szucQUFWmV2gCzkL/C77ke3l9rPFj9rI/CB6YPksaAKaT"
"KqX50J3PgdmtbgRKvDIK8mp3eAWNXR3ZWfcfjoB6/BXsRz1fKKAzxsAE/LylPBiS7bgIUIKEBzwB"
"gf0XbECNo1tmlZIBpifQbaRdRLEi9IzIj7CyQaylroT6CnvVBWfNObCB/o0cdjImF4IXlPDB7Nic"
"8D1HsYO4eHxthWnZ313QN7g2PYdv282xg/8NsOMyl+IFr0FFjWM4wUBzo4/BSorRxltI3IsmF9Kz"
"/ONt50E9r0655Ysj16LevIWWhcTuaWqAjU2XQ4ptF1/nTU5tGNQrgZ/ndDF1gRhtvSvwFxN9vMF2"
"VNlfR2eYPGkemIKQMG0hASZuXFLnB8rfH5hPjaK+yst04azOk00PsgEBp/QcT2RFkFA86tgN5h5E"
"6xaSxgTmHjQqAflXT2yY63fmqGNKUpAQ5CaiYxBs3TijJ4FhOjOyjEkc24/Ervos52HHLnxkmDxK"
"KT6CPAYSg22xi05Z7IDbMPqR74PzMFowDlwCm4wBpPe4NiOAAQ5ckvCnJpe5RR5FgMkfTD93gbxj"
"PcE3vbzzkbZxnLoOnSP7WQks9sb5xnewQr6Vj70D1Y5H4HEBuP3juWpQPIg+MWTBtPOd9nKCm/hE"
"XAagsUOWToKGa1dC/SZ7YZKRIwLjyXRBmLuR7P+Fuo7OVvjJwXtx6tV40DSdCUBePVuT/BzWCY9I"
"+Li69VHZu3k02s8fk42dXW9lurqUjHPim2XG5RHeAzciNAKGPe0rfX8aNuglgLhrFElf1lUfy4G8"
"IFWA6hLy3vAxdBo/A6WaAQi79/MRDuNNdUVNqEQZPIX6hhzjrFPYYXsbdJ64WvZDg9tY1g+iFeXD"
"7VerHv9Wq271Vqv+iRtj3zJYiL3BPJIaDVcg4P5kjkufQc/IJ3N5ciaXdi+zLTGeLJhl+ezldoCu"
"RkrusSY5ancbzKb3ceLGdZtExImchh3lO37fSOfn0ryqNDUEOXvRo0FSPw1lQx8NPuo4+1X3staY"
"H5t0PIOa35XKJqfvXtUBD1IOvbQiaq2O8I9YDj24PTSnMJ9QsEXO1wRy0O40poBqTwff5DevmPjh"
"Ew1W92JfH9JkAvpOFy5epgaVVrGJcW4rm55deqyHEYMqukdjzTu8fYKuIU1sqP8nImYaW/gRI/U+"
"Yy8CSirL3YrGBOqNc/YQuu+pnXhEgoLFL1orPQeAnL4ZJlQA5dzClRkbDgIesR1WmYf/a4Ojd1Rx"
"H+Lk+kyPX7jNYUKqrmSNX7nE4cnjAbOdcgKPTIC5Z8UAh6CJ0IGTA4GDtd0PQibkDHK3/Ibbgbvx"
"6LBdtLfgZDWauQbKWvpW7f9KSoiagBEGykrGS/lFmAbJmACCDh18JQ27FuYPsmako8CIQ+jxE3hK"
"mV7Q0/yxQwL79tNv8byJo0/JmTgCz55pELGfEbfuV2YB9ZiBioiisAEaBdCFIWZjeSmyxiXyyxyA"
"j8BI5w2el2qfq03If225SDg2xalxDivu4Gvs2Md3ODPcjva8WzAzOptu6zkqUOetz12K6eA/RG7i"
"tGODczBLvxnu/QXNpoQRYgXNbfHhHZJLnBFKLuS22v2BnsX51c6kZXeVB0x7YTzqdCAyLk6YAB07"
"r3r8vKuvQUUznM2+wQZVw5ehZHPPwz2yxa8A3D0yQft51cUGdoWPmKwRei1gHU13wTCYYqImB3Ip"
"vrVBg0B7T/26r7YyAV/cSoNBWS8Y8rz2rGtogb5rHHbQjnKDzdD+8emWdLr3gyGaZJ00aljE9qmD"
"v9yggnn1AuNhUoSLdhsDPOf9LsA/VoHZ6IiGgeFkgawAPA1eDz/3xYtK/J+Ay2cRglX2wc7auu1h"
"zP7+Y/PL2mo/FobVt4Ejf5xRkabyz9iGEXVLgY5S8qPyx21hABx45LwoTa0uQR3gE3ME/7D6IGzv"
"OPb7eN9dmSZ4iA8neArGFJ5Nd7EAbtwCp+A6zwFBe3p6xsXFgTOeGBgY1SnTwwjro74+gZG+mZnF"
"BZHQ7sSULT8/Xx0dnSHwYW9v39XZ1dTUGBEZgTY/n4CDhbHgQ62srCwpKSktLS2/NycnJ+/y4EIH"
"jIaPnTnxYL8He3v7j8ocERnp4+tna2+fkprq7e2tMTfhQQGQl5eXkpKCjp89NTU1HR0dExMTMzOz"
"hYmR3dzc3N3dua369fW1peJiEVFRQyOjjo4O/ny+mJiY+Pj4CZGgKysr6+np6erqamhomJubP2FM"
"TEyeprGxEeL8dHd3j4iMUlRSjgoJWUt/IxMREREUFNTR0fmgKCoq6ujoaGtrm5mZwQOFSE1NzcbG"
"BoKGPpeX0c1MzaDCAJOXn9/T23sIJSMjc56uh8zMTD79cH1GimGOzczMnvLBwYGGj+3t7T+kz09P"
"5xGgxsfElJSWeHl5/QIkJSXfa+5sSiknJ0dWW2YvHh6eho+dnJx+wcXFRUhIWJ2zFXFJSQNDQ0EB"
"gQnLy940vln2dkqMjJu195x9CwsJubu4GBsYREAJ/lgCAwN/Ymp/JH4yLG2uAWZ1FpNZjv8kJKWc"
"nZyCAgLKSkvz8/I+sH5wLHwybAA/Pz8QENDDw4OGj/82qKCrq3u4dxZOdAFBQWMTE85W9i9+dVx8"
"y3xGAsXExPxzhp16+JqdnZ2Xd9iff5nj4uKe/m5utoWBi5WpEaHACwoK2sIEi0xePiEpqaqmZm6+"
"6L7HNA986V8GHCEhYdaRnbnxHmwO0tHRQWRArulRIZ7gyMhIzlWW28/f3/fPT5bcbFnOpj+CseHB"
"CggLA4aGjwMNDSNjpg0LOxtbSk9IQDcornSKWYur1Z7e6dhYuHh4eE4OvtHQADmgASa8CwGTgaat"
"oaKgKaWsK6OmoKClER42cuYOGRERUfLPbVk+eLV6OXiF9/X3d3dwyEzJam9v9fbyVFXRSq3skRZS"
"0wNlKOVtJIeYGyfkAbdVoZwakfxa0fz6aXNHvwSk5F2IgaV+c/bKzc11nGXKnJWddba7u1toKAhO"
"eqt11lQuVy9mW/Qe4l7ynPsv/Ha4N9zWNmCXtqNjJUCha6+poK+vjZctGxsrCjJStqilWVZfV7su"
"Hge1VfNc7Tu7WPX/9fJpaWSvaWRQVk7a+f0Y+TuEVDyahne3l12cHTOKiQkAkJGErKGjqSGlqpCN"
"TFhcWKcwCBUJwCfNidCJQH2imsPNvxU53ZmwONHjg+8F80uQ7Z05hsUClReXFFaW1LGRWhmSMj8t"
"h+WEnKqk3MqknPLk7MlrO2cI1LlBKQXIWQ3LWQx8CVqgljaaljKcljbGqO0K08GW6OewfQwCRUDk"
"+HbbWk/qVvRsNvJ17Qri9mG5nbtGH+qKDuydDUUuL6HJgFFaeNG/x93NdXLLkRXh/99fR8D5Qh2F"
"lRn7eMp7BFrg4TGwhI2NipiblLKzq+Dj009bKfGwu6cHSgcAEpH42HPzVpJNLhkBIfcL7Uk13WmO"
"EJ74HyKRx9WwHTnTtYREsUNQUPDdn+124vtiQbSYMgHDFRGC9+BGnp2jz1pAqGP9DZJPrA8Ziq/w"
"9kFEHTAxakFQvHX6idvN0ok9NzEVLwkVHwl1Dj8JDb++f4Cjq+KhIu0gJeQSExMTHx93P7KiomKM"
"Vg3iUg7MysrKzMxMT0/fvjE2Y8VBmorfnTUpKTFKhr3GV19fH4KGg8YV2dra8m1irGbmUVj6cXqt"
"p0aNYV7mavz8/B60AEdw/KUeiPlUnemxoT+mtPyBwQsbjxFYtmKqmlqLSiqfZswQPSOTrq6uIXiQ"
"kZHaWa2oLmeXH9rU0hKG9kFNpD0x6LmlrY3pnj3ELeiF1N9MiSvO/dnvEuLpFz8UDpulelkF5cH2"
"Ym1t3dHXVFFQlhXXikSs08hKjR0NExM3OATmLfrlwMziyu/vb9L3AGShi8ejxezytMKasmZRtn50"
"TZxDEwst3cJFJJWgWHg6wU70iU3JTAJIYFZ1HT2LuczktPECAwJ4MaRl1ACFiMtKVcjNy1+mL3Us"
"RayHPlmD8ZEVNEzcReQVkwuaebFttq+/PzUzZ1J/3PTh8yQrPzQ7MPz3mJ0mAvPY0dsfERDqbpYm"
"6+Gsh9+3Ji/2WnRu5JCdhWFk1dR0LGVVDT1CE7z895V8fqoEXGOY0iPoY9FWU9RcWettkSUl6H+J"
"JdZ2FdTVlbWPwDOOq+jH3dWIRlWgycXDuyeRf9JbX7AVFhaWQ8KNy5E1u6UaZa3vqa+/Pz/bJzde"
"rNCImHoBlc6ZJE/g2M8g2M/g2A9AGD+IlKfPICuHtysHd4/AmOuH0aRkFaApmWW1DaEdQYmKgAvO"
"q1HDQ44T1IcaBrFfYLwJ3u0gPYelPhWrqk7ZCbtn04vbixsRlbUNFfQhadr7WIQnWYQnGLkFmVqG"
"KJtZ/MpBiQoIy8lKK2l+TAqSNRFRAhnZ+m+O86qb4TehKG7Eax7TaJkfJCHnpYmLFSERMan52IyS"
"en4R11EDIS1+OOZrlWuVG3gI5ulqfr23MganhdeVlelR4UELuIYkqyjryKrpBaRl7/3FRkT+7T7F"
"26cPVz+II5NzJpx3x0Hggf02wYsDh6qLz9vQys9UycBCRVGHGyz+MwCMtfyq6eBotGsHV2NTy99Q"
"xG+fn2DwqOBw2PqwRWf9wwMFgdBq2qMsIfz9HbbbxxfgyARgiNgQSHgfUVJBwAGpoCKlLofIwFKN"
"E8IhOIr15Lzq3Iqu6g6RVhFlYXn9pi+2sblVQ7TVXkvcXkPSkTVxN/gAsYsfAzNPMkW13PImFnyy"
"19hGQ02EOysA1NPgrBbOWvS/tyIjzF5LysvfwsnZY749IvI44ixjUvOhqWr8rOXUjDXM3M0dA6Mj"
"4rl+8fLyykhNLMOxa5sXJoJE1JUdrekxo2EkFNPzizjVnBjUpq2roKgmhNBGw1xBu5pP8eTyTjKn"
"XaGSnJof2HpjeNfoGjhJqev+iK28Ix6bQGTA/8xKZprF7LKUvIqs8pbQqNhx88sIGF11oauXx+Xv"
"gukx40u7Z2tH94sbpx7nb5A4yMjI3Z/VNHUISKk/btZ8gpLGmAl7s6t7qNj4XaBiYGxmY56irC6v"
"Luhzj44dHSsxKTUIwuHs/KL2jPnL08SGs8BRwyNjs9Nz28tb5+MTywtrB7+AHbNX729vkNjx5GVU"
"v/deuMhJKbePz6empm7k/qcuMChIrjB9mqelo6CkLqciLZQWG0pkkl5/8I/txSNhvrONpWS0BcSk"
"rLyie0bRlJaWxsfHf1JSBj8ccWFAKmwahaKtc4bhQQvJSiqo6RrklpWCbqGwPntqqCwprCbocT2+"
"5JYQNXUIbhhBtwWFyPb29t7eXkm5ayPXZZOzc9orWyYuDSMXISERCPzB0cmppobA8Pjz6xHlFAxB"
"Sii81iWVNKSg6YgKyT5aMgIXk9yFvqE020pVmLXp4BEDJi6EcqwXF35T/uWpKWjHRSaCHn5PTx/Q"
"hDMr+xsRrd8d41ML3sWoCdvj0wvhBaRklXTEQUgDuz0uMYk5vrh8GBMHIxsPqbkYITntYf6dank0"
"9nJxdXNzDKx4aZWUEP22h8/PmB09KzM/BC0LLyk5NTGpuTGj40NjYZ94NWM71utm8QsQQob9apgQ"
"qqAkragmh4stcWBFBT5c5lZe9BwUk3+Tvf/995jxz/gvCioa6tlXMjezC3unV58Xr8CT0zNe+qCQ"
"sJScsvpOsQkbx8ND4+NhZXziAQTlSVi2s9LKTmWk/LzVDkluqqlRQ/A4VC7ycojTUlOODYDvPLkz"
"dx8Aq1vHqxt7r99dWWWBJ7woaHyB5+s7KirqwcFBWki0lGRUlORu8F4u8gFjSWS/8n1POSsri0xp"
"ibC1gjKi8QlCTiW708KGwp6ELUnQo5wvKSmJjIz8qFl6dS1TUn2ba2Dhxb/N6yMS/e5o9cKLkfRw"
"AULIo4G6BO3ueM2uTVhf06uCZDXRN9FDA4WyK1D7OfEjIyO5sO2f1M3Nzeryki9woBOizMXaM4jV"
"RGEsDUDalA4ur4iebR6VPfTIpTpKyfZCo1SMEvXmqChPk/OJc+b6CygMQCcLIJ6x9UlbYbY+PU6O"
"n4YAAAB5u6pwVEdhr4hE0Iucpi0ZKEs5KKuZ0tRwjgN6mW0UMKVbCsj1lXCMcB5Xg2PshKXb8kj0"
"ZdNrBsiPxHq6jp+G3swNhADZCyDirA5H359EXOGoAM89rB7Z6p9eke5MontSF8YlpA7pyp/g+dgF"
"G7N9OLS4H6BB0ZEHKLmV8si5Z5NpvYfKqHVIXSFoZ51DcTM2wimgjAkHjaGbsoi2A0FdGQ8+sBK6"
"alxaQoz0L757fcGvhuL/sWv1jkPM2IVqUk8AGsctOg3R4rco4Ln5apNwQsil2R7LkU+WtlhG6uat"
"fPs7u84l+iBPc2DzpzL9x5LcAQEa/5WkgM7ErTBfi6P8tEX7a4k2FINQ1wkut39QYy/KdfNiv0t+"
"4bVE4r0UashwGclymQjyRdIedZRA1JDKgd9/9c60LwuJA2ykhZvTgO6uRd+XByqLhw/LmR/dnqHP"
"88QbZUO6CE+au+XoLzwQ17mq4GEvDUSHkrt3a/lBWgoxFQWRnuhFEZ7B6y2Y7vy7NzOJTWRQny9d"
"nY1FW49GWHBMyS1c8U0nr08vso2LFzOZbZSQ2ctCsGSGkOmoHSvOhiOalyBfS2g/mx20CBkLwrGV"
"BvD2YWBjBbGT6/4lVI4jiarFYBdiaB8iyM8Jo603WQciLNt9jTCXBuKoi0LZmQ0goZGmHY3t1HCF"
"W0qJ90BD15AKp0xysCGsiXPxZB/cegJv0ak8IBE2AqNSOkvPOqpFk6D1STygpmf/adEbPXRRZ4Qi"
"qnHGGopshswXlludvj1spGkKIGJurx5NcMQaYgKnlpsWhpwAEZGdUpTp04DURMqZ5Twa794ZqInt"
"EWH76SNNdRhNdMQUYDycFWjfEoSAkqhvGSoTsEMNG8lyxRBgYkCsUCE6MuIyHv8KHl+4f4f4++OY"
"awO090scIMdxfPWe2ioe3ywau3PlTnDVrmVIb0nSwc0zargIr0kTXN+2F2NgT1wACuICFvciJmeO"
"vd7sOR/rlNGhQTfX63O/MEByVe93VyvyUhnJ8p7OcpnM95jM879yEmYNpbk68kpNOrq6VTgpQ/DQ"
"WM8CKtsGBkfOAjrrPBrrDALzBBzjPyilnY58b6laoJkPyRIcEaW5jUZbDUVYf3HkZ+EdvFaGD9QP"
"keqcFOucFSptlFv8NfsDjErt1VMMRdI1QCUqimTpiGTqAEjShBIqiDdRkd00HOsKHmjJA1JRcLWV"
"5rKVgvSxm2vBDbT2hu/PjyS3kYutpfJNJbOhyCUaySTYwS12UMOd6r+b4riT7raTbr8dY78TZAC1"
"uvG5UDq2Q4A/rmXXvnLbmrS5z9tx/Q1aAk06Qq36oiDz9nGa6O4T4yTYg9Q4jyvjIjTjMgyD/YYk"
"3/7J6XMCJ5BDQ7aH8peSq5eFGc1ibaIJOZDc9EfRHc4KJtACHJOdyji7ygTLmhTDhjyZxnImWvCi"
"fjCvT0+fz49AT1dIzyfUb0cMT7u0V5EyNQSzdUGsdi5dEMo2h8ay9Sg3gehFsCeswBGy3U1C3e1d"
"HJ25+GPv3jR6WijPdyR/Pwq89e+uWpKJ8D1Zk09Aa0fv05LPV1pcmsa44H1QBSdMMFKypMLSCHUt"
"Sb1LqxXBeqK9oZ3QU8kr+OsY0+A09ZDPiFWpwPdClEluhtTCLh+3Mbb6PrB/sKzoTIRQhIkT2oIE"
"g9uEK2Eq1mdEZkANrWysbPTyZF8rhkdMAx9krGUQq5EYJB5tb4eNJfzd7z/WL46ZTv0AJesik8F9"
"oUawsp/d7QaB3ZUHfJ9vn0HQTj9MNczoUu/BrrYHSoc0BprRuQFvndtq0FRj0Y5WIoPRWbG9dzJP"
"RFhknXf8HVV1v4GaTXUS0UxSrkmmaYYblrUhVmLBXkETWWMfNc/V6OKZE6b/sRb0j+f2QQPQn2OW"
"gynuc2NzUWWhpp4L+k+dirBUiF0TgpkEkM24FRGHw5TUOk0NqGc44T0Z8tBCzankVgw+Lr47k5XV"
"3PCytaJJUfUbG5iAs8c5AVFDyZnblvgTa1L5RabHQRfB0ibqwxEQuKC7b4XxFOAFn4kc4p54CHhF"
"s/CvWWDmkstop68xCyE2hewfG6qYq+ip6NM0GaIqyAobd4PMrG1poSHuUDgwde619Eefxeezcdbm"
"14BuIq86F8uZX+SuY7YWXyzg8+oW7r/S1zAKSnjFmLPxIspS6xQEvDS4MqT70RcYwSDB0wK150k2"
"72QXseGQx+Cg/Ts8KRRyDo2ZmHJQedkFETwUyjYEWOzl9+CyPFTNrr1LKq0i2DB3PrYJhb+K7UmN"
"CWO33ORoM0tLBLvE0kuFHdm2sD/xmIIYvc6+F8nYh7bxVIIhhJGuRTSdy2O3sDn8qpaAMor+eLet"
"LjUR5MW+cl+dB8oAacYNp3p0p4b1MaJWpg9GHYTqzqEuToPsuuslXe++GlpABeSbxEvEBSNDOaax"
"QomGtPz+Qe5yU5zk/wbX744yWkAN1L7EnUmDbiyiC1aG4BxHib0skPmb6RHDmAMuCJQIr5Bd5y1Y"
"ezE8wA2Y+y9Ryz7J1u+eEmSFs4Wa8W9iuqSvBOul36HKKd1VLa+r15ZIS5zZOMmXp4cCCILft11j"
"1RyDkMAUu12dhO0Sp60ItuJp8sJXKACXEGd1FVieXZo4M5NH+4hXxEgd7GpD45MwEw3088BVtOIN"
"4wlfsOelOgitDFE7aY4pCEdZEUEfjFzIsEvEIKvcpKrN65MYuLKD/K0bmGFMR7+yagUtypz0Doew"
"XReGcVhmLC9lgEg5as8vLRfRhS2fkl4GLg5uzZDfoeoo3702ntceLyfPzMVU6XeJPQl7sWqR00X9"
"qnM0LDTBoJ4HTR3VtiTbs+06FtLtYkADhEQR35VTD2Y7t+hB7G6sPzb09CQEjMIN7QZprtUTC4li"
"Bj2surj6oOx7o9g7wTHjxOG0rKfUzdvV1dPNiR0RCSUxpYVx5ea8y/L0SGJMJIQeU42dk5ZYjAST"
"paGhsVrN6/S4iPg2j9elB2WJhZ3BbQcUREuJmkcSzUpI1mTU7Y5bS2Cu5JPkChyImmOtWZHliKWA"
"l9iwmJ+P77m6MeHpG6UHEdHQ2d+tjeyAwAAAee8z8QjPZ81JABKUgajBOvZ/zzPnT6WOlMOSbaJP"
"5XDlH1H03ctNmc8RwdgBmfd+d+GNd5HiGeXZkONDDYXiJ4WYsUZKGYDXO7XQTbLHyw7LqgTkhYop"
"shEAlYeopY3X0MvAnz19l0cFOhCKEVyt7lZLbOZLHeBv5R6yD0Dpizm6Nx8HkWefWzIJcnNjHrTG"
"gIaIsjmyFr1KlEMN2ODk+9AsM5jj9/rXl+DSohbOBd23kIuERY1VdAQFBIVAiYud0X5LykhMFRI4"
"8djfOaqWvxpaSwto00PlzlGVQ6NLebEw5PjYLiMnDY70+flR+NEOBdiAeLow8xCzvkI1EljrcpOS"
"WfXX4K5jzEPng5DTDOLYNNo4gZmAMeFAA4WI08LA4icVVex5yeYy2zgFkoeH4xh57oqKR4qIqRrS"
"0FTUkkYUjaXbXTnasHt5ef0CxpoHGUUQOzxK9gF4bOP32hbuUrNCixs2F5h/pZ1L60trMysxbQt+"
"wcnJycGRpYeZqQhEzlbZQvXX8IWu/cM8Yexp8JrYXKenzZin9la4s0IHH+SQlK3s6b28ziN8d1uX"
"B7BF7qIiUlhC2j90Su3rGRHOosOm6g/InyxIqWUz8zOkVzjPh3fenNEhwUgKSewqbuxjCJ1HqSeV"
"VXJE5a+t5zYLaOzfOSkI3HlNGebTxV29OazR1/uXfMUjtgRvrOL7ihhdnae2EogcGdiTAHkW4ulM"
"h5OItwGHyFeB9oGngvg87IIlRaRwxeI4GK3vowoadTJNtwhQzOL9Mhldgye2GpAyjYsUJH2IZ2pq"
"yjAHgapmuLcwyi1iF9nHUOaQMMG+GbPQjkEJ+GEgYMaPN7itwLBA6wLT6oRKrEUgoYTBIzOb4JjN"
"DuCh1EfAVRgFUdmPIjSTzwbEZYMqGaTXP7WX4BKIjo5m9HFsSenaY+Zhvzppzhg/niSE3gu1vUiT"
"8kUCTf0BAYy39dFGJeQlPkZmkKkRWp9Watcv+VAnb8sHB5rYG29l6frTIWK0wk7m70DyDx+CkL2J"
"MO25YSVFpatoeWaN8dI1pLvmyuVX53vmTweJ15IVfPuc/LushMcYn/svtxvRpEVENoYQC6Aie4nm"
"rCZI2JAlgRRRTg20YJhqaJiS/fWyCZVyBe4PKJ6smPJ1xTQxk7RHzJVTlZCi3cUMJ4G2QQvL6jnO"
"NIQA88IW51IB/8YS+CwaJ3IXamHAyGFTxMJFgZbggp2+Usc5ieriouoAlIklOfhZToCAgCVbcGPS"
"mRzTxQTalGwVS6Wv5LW+ORRQz8DFAs2f4I4Fp/nTVKxTNFxLzCdhoOw4D9E/hC6z+x1LKZ6wnQsp"
"cakP0u8eZ5OjEVUV1UuxiOGRbxyVnsOuCJUcpZP1YZAihA75k13JHvnyJvl8Efm6vVAr2xCTKSGg"
"7o7bRGqxAJ7Cio+wmzDg9aMJ6RfPFpUU8XYwXJvZtJVycc8L96OX6caHO/a6IgNcLAM08cAUdIhD"
"6oPUGIarpN290drP0tLHIobtkvNAX+AA99VD3NXyife1NPJ/MFw9Xb0TbPmx6qPtlikBrtFUr9FW"
"r4GaP8G03YAZjlOt0dSnEdKu2V+CIDjGN3j0TINkabR757uJ1xXUgW7iOv///2l60BDKRFguiTrZ"
"oajaob/WoajeoWQZVYMAVVbkiEFJlslp0CmgGgXii4iXb0kquVgdLZ2NXCkJ1GBBYbRZLNrSohyM"
"0q0k1a0426c60iaLHOa+cMsduZEgrqhlNZ5BWs5VI30jP2dfSE/wDRwpsKPBDC+GpENnXzMTMxGR"
"weqhbHYyRHzZd1uZprQ8lgERPYPxAENzSfePrq3ZMYFAjg+c8WETbFvzeQE8/j7tt3b0HZ3x9niN"
"tvb+DoBJTORMG7SmhvpgcPzuFm76Ov2Z2TPlSINFv4Pdn+2+d4NfwuV0dipGb7CxhDAuGzoCbIaq"
"1y15RT28508deH8UsOJH+k11wG1DQ0MqYvAxfNnY2OBHDVhzMM0ZseD1rcIHjRYXF7kGpQhLMHJy"
"ctoRfl+e7b5/FICChwoKCq75O/VoUyDCBpes27XpUSHPHLu061Up0yRLXIaIkcpt2WNFCL6Wto83"
"nlpK/nziSxWoTkxMTE1NEabOH42Ysy4JpcgTxQmRGB8fX/7NzMxgRQiSho+dWTHgQg+cemK+STYX"
"uoARosZvDt59fssZseADhYhjQgaOsUGBQgSKVipBA4SK9oOZmprC+63jRQk2ebXoU2UzgK5hln0+"
"40UJkKzbNanQI52enn561kX4ghsaGpqbmxsbG2FAAlZTU3O9Yb0AfvPp6Sk+Pj4uLi4qKiosLGzU"
"bX5LSkp2GXIPTE5Orqure9fwE4EMDAz09PRUVFQUFBQkJCR6VlVVVWVl5Zmx4W2wxcTExMbGRkdH"
"/+4BlsEYGBhoaGj+HRERcSt4PwICAl73XMPZY2xsTAZASkpq7PQu4j4JnfdBICAgWlYmfjxTfmcy"
"NWxtbW1sbCDDBOvs7HyZrcAtFBRU4qfBAYFGnVneu7u7W1lZWVtbP7tJEaAaGhoaGxvDgzAHBweH"
"h4fHx8cOLiYmJi4ufrs9+XDzQYB9HhgYGAgISHd0dg709fU3gevX0tLyiqHwtLW11dTUNnke+m3k"
"wfT09H7ueisvL49w2aSkpJSUlMTExHjiNnmLRv/78W0Bzvd7GjpBRHOgTQAC3tlBO525gWGDiWzI"
"zL4AVhrK6zuwYhIb7035GtihKWgVn81wc9NSEphyse80be1U3ezUvFm+628323c3669t12zrenOj"
"O5ZafUTEb2MjQUCg/jDSvaB8Rcl6zxBkIevzJm2u7q5iOi32LmHkokNQ4Ip7M9E4gnWunC76wPPV"
"dP49bfwNzsjYqV2qQX/gov96lm8jrHrUPm2JjsiY291XUxYkg8YGtAU67fF6lq5MEUrbEwIrJM5Y"
"HiJxbsRFYXeuXP8HOpjZPckpXkAEtI2Nr8PHlnc8XKr24cxooXwKFWuc3WV4O/VLf2hSNPPm864M"
"ccqs+/zpxV04HbrFZpPsOLVCV1DTDju1IN5rEOqJwT7lq++GERadTVxkat93luWeIkrTFxpfvaan"
"yd97r50rdDNviA4dOJt26d537nioqIUvpBS7pNz1ZxElTfXPyNbUOBSVQ6hotg7DcCSX8ihB2Z4r"
"sBbDf5wg+Ag1HzxdImOwXtWz1DYSZKSKakXYxprySJYeTHql7mfjucBEnLPdKweOg+ySVkK4W7wT"
"cbYGBtO/ZVoAvSaMGSccdOzk8n9wyFtHZ0VHCn2wDiD6eNMOOY1tbyOSMYzCasonc7dfsv3egZwt"
"rzgzkpqec35wM3avHghGr2ZL3LuQa7ik7DmWgArKThzaZktp9S+qXQe6OgcUXRzvujp5wlr2Bmvk"
"/mZL+FEx6hnoXJ9H5vw4FTUaWCQZ/+h63tugnZsbIKaDbit2/g3MT5Pxr6jej7afrGBxVf4s2Nx7"
"z0Gt6HLwfsSdJfqGlwGyCZduaX3k4YTtnfzIXuYu6V7kwmGN0iI6Lf4xxur+zQ3uttLPpOy/rX54"
"ZfrAgiul5uv5Ohjxq2iGhUNESgPankLP+AyuJyiyu77puRAVJJMhFHaY7005z/iaDiFgEEgtJU4F"
"7r8ZjZOM9rd2T5WDctFNO3mR3rmh3dCaaop5QRxKZ8R/7slDP9wqffjf8u5UZ9Ve2oZdKF/FIXd5"
"74Wg4lxb5FTwcXz6bgP1f6MaOOLyfQIdQ5wn9NpZLzJteujk+pDS3tZ7uckpHZk/7C5jPrZRP21u"
"gr92GZvdN8MWDJl+3dEWx1loqJo459OewmZrJGr4WItzq/xiCwB0GI0ub3x1/nIjlLvkXpvcKks6"
"KzzeePl7dz16ZbCubgaDDiG4EmCJ0TvfvfLZGN7TZ71yYJh25gle/SRuTWw5XcQGiiWFNsBCGKJu"
"4vnYgdRGcQeq5sByWMThYTWvgRw9bnNwDZ7NgebAcqT6mojRSnk3gACgXyHY8WSo7Tiy6TdIgnYf"
"V2KW9kASvDJp+cfUvAmZ/OA9hH9Z+RD2ONXi7k6z7rVCv0OQmYZPG7xIYjQPJiCJAffPK8G2ZtWA"
"jCem1MECaJvUAXsCZrcog5DN+NGEOaIaNjQ0VFVVlbjX2dn5ik1FYUACFhER+Z2goKDU1NSqqqq6"
"urrGxsavCFQ4vPDx8RESEnry8PDwxMRE/ldTU7OwsDC4V0lJiaPFCQ6Xnbnx/cF8e1mtrKx2k/L6"
"IyUldUPV0dExMTGJiYkJDQ3Ny8sDjDqP4N5ewb4jJwd7LXXV/p7O5rrqqoryosL8pKTEMeFAA4eM"
"e3goJydHhnVevc5/kaXJEa7f1tZWa2vbxQmHEaHAA4Sar/2FcWKCna6/w8Fho83nhUr1yHblo20g"
"GXN3aT1bKVW9adDwPz//0U1MFJWVH0KuPDw8vE6S9PR0vrCysiopKccD5Ym8OxtQcNcdeTCQote1"
"wr/0B8Ob/8P0glnxVOMiGAYb41eFBHWwM0jCxZM7JyNqRqIKGiOTU73c3D7aBwcH6qbe5YmRof1S"
"IQbAbmvoosi1F1v9qRMIx0vyEHVowSLKXBSdiBr4c9ciEuhEaWhlIhtKxLga+gNNZCMjeTMnDk6l"
"j5NPqy+1tL8KPPdz3Hw1VlBQAFIMlZYfi0fKUXFgCkUFlKcChL5L8j88klQEQjlzkCBPnEHZCRfL"
"rytYnRVqchlyUdNKaEfliFhthDb3c7iuKiEdU7W7CQqp2DPwynX9UeLNGh/PJ85GlrY/JYfNMmTZ"
"6WYgJBgLHeOj0zOoSUnmIB1KwLgWDOOnmkStfiEfTscJUosLuE6S5JT0FiXrudL1erDiILWaPcVW"
"6oPEs9hTkAr1PbDN1FUgop6LmjjE5RjE2R/k+TDc5yrekhcF0HNYqeYy0U1xjutLWInwcb14AVcB"
"bR0PBeWc12uCmdBOTsDaI2a0B637B91Jk7zuRcnibBzO4wHOmD9FMPDxNw0HFLe/GriwQr4pqeZ0"
"cLnQ1NTwT2hNHh0uQs/ykWJ5fR1uk7xOUFAJ2POAXmJfr56S4jK+sLe3X2GU1T4Z5eWVs6fneYaU"
"ZE1cSOYdCyDEa5k47uGs99uCaUZnZj2XaDsOowwZom5OAR/mloO+0lKS82cOPwySKkF5JbCLHl99"
"AhNGSIpYpTOjhqw0rZUy/lMOj0h9HUaj3NalQkCy5R5+bxycv1qSyRGh7B3Zh0WmD9DJmh5gnhUV"
"svemh6cRArpxJyJ5CR4sQDe88N4jagP5ueEHLU6TvFZsSMYrPz9/FlhvWXZRl//wyEnnUhFOcY6L"
"S5g8mqbe5UmvAEipZ9IR/rLmKjBQwwWXcH0tSqPcJmDA6ZVJ/w4curo9fmWcOCkpKRUVFU0wbj6g"
"OMcnIiNza3mGhGR1dBJ2Ao8QuOjp6aWieudP1+AkBJGs40uVHZZouY+OeRCmYjjJRojABhYoqJXQ"
"4DE7mytPd7cvz3e+rzfRg1JL09BPPrt/GCEdVzK+8M4sz8DEpIhYWEfLf5JGxLt3RghGo5wGvrC3"
"tbDwBJ/Zup9fAbsjkEy4jCmjuvH/Mt6cfs3R27p4XffKBnJMf9Mmox4oQcMq7vMFk/iGezVsB4f9"
"SBD3Js5aPyJMYhKuPZhiCr+AWK1uDUw901+YJhU7/3Mk907tzRsZzpkicUwFBATXbvjjzh43bFEB"
"jrhTL672xho6ODjUzY4/ZfDLDqXWss+oJJqG5bISdoGhG2wcUp26t5YGBd1TqXizzbX7pgaoEzba"
"IexypuXIuq5RN3yS0pJycbftCGIV4hATZvPhDU6GQ5vRFRaEYB2/MBySqiF0kItpRJ4LEcGXizOc"
"kjzyZexoUDObm3GnyksIn6xqD/eO4sLi4j7leiuIOnPQGrMlvUc3/VU/mZDFvBLmeraY+Hop7Rb3"
"Qf268Ib1YsjCzz38PfoPPYy825dGCKK82xecbG8n59HBA5NVsrU3MPJh420+dNr+jWNFsKlHL58K"
"rgMoAa9BUxGQ6p5uG6LmxBaXZWByRQCfrKlmiDYAR3hzuNSOnnb7DV9sOX26JtNGCTUM9k8TMiHC"
"Uu35UQatqLo7tUy6W9058lmdv/Dzc6to8+hHaw6B1mupELdliedIwCDCQuXlac7taFO1YrpgxaFu"
"e3R1dV/h3rrwiAv370GFLILma2l18IMYj4wiEKDeMyXtaVO1bOnytLK6AC9RQUEBRlq2hqvVKVtb"
"W1MTE+5fy8vLGxoa7h8dgUU7JVYmjNp7qWD3ZYnnSRtSJ++xtW3GByW07GvH/Ly/j49P7sk+SHpn"
"a1dxXEMH+6ieGiUFGQcXNxTOxen1AwA/b5o6+geZKybeiiedZcU70X0IqOxr+8JCP+XJ21Aj57G/"
"lxcYEOTr66usrDyEIyhe9iVuw+QkQBqbmjuHx3vVdfo3YAkrmjU0M1n1zx5LbqNEpSU9chtg4ySx"
"BXfOzenSUpybc6DMUwOn1LxlKWNLmvrTU7IgwgZvbGxk84Np4uaOjq4+EQkB9dmANAn8W/D7NOBy"
"7UCXW7Hg5uqirq6OY2XsY/azkaCrhAbGzIHPmJQXV9jzBz2m1XVHUKYkdM741w44FqN1rWhzq2x3"
"AARJOpco9oKbTpetvt9xsHy9/8lCOSSEFTYBwB39ZD4x0SHZFZcW9HehRg+86x9j+LOxacwbBYQM"
"+PwVmSIyx4Fy6kRjWA1QIohCAh15hglmanknhMrhdCE3e+jgcLBFh4f+4+Pj3dmZsAi7GavkMr4g"
"xtI+hhCmGJZJPYCLjQDwvNn82n+eHMaiVvIf4bfwjPjqbrKYRUgmmpmx4dXV5ceQmoIA3oq65/T1"
"KVRRItBPSzbFC02DWhXkhmNRQZf1X0xpfkUygGy4DL5pvRpR+rficelFYdmy7xBYI+Bufux4nV/N"
"Ea5bpgIpKREbq9msjKCU5KDEhKDY2FGTYcRloUsrmVoreidpJDWbZHSalg7Br5oE0793oedEQsfY"
"3PswNHt/mOsRnHTMrK2trL6o+YcbUuDNP9WGKqZ6Yc5drP0JrBHemBjDsDDwtvVxUvQBJ+aOzFpb"
"3EZNx3aFl6XJXYCUoKGH8J0BUYiBfbJuclo=")
    )
(setq cuastan(CUASTA))
    
(defun c:esbk()

    (setvar "cmdecho" 0)
    (COMMAND "undo" "g")
    (setvar "osmode" 0)
    (SETVAR "cecolor" "bylayer")
    
    (dcl_project_import cuastan password ) 
    (dcl_Form_Show estbk_Formulario1)

    (setvar "cmdecho" 1)
    (COMMAND "undo" "e")
    (setvar "osmode" 1)
      
    
)


(defun c:estbk_Formulario1_BotónGráfico1_OnAccionado (/)
  
  (dcl_Form_hide estbk_Formulario1)
    (dcl_ComboBox_Clear estbk_Formulario1_CuadroCombinado1)
    (Alert "Solo seleccionara los que contienen atributos!")
    (f:namtag)
  (dcl_Form_show estbk_Formulario1)
)

(defun c:estbk_Formulario1_CuadroCombinado1_OnCambiarSi (ItemIndexOrCount Value /)
  (setq bksel1(dcl_ComboBox_GetCurSel estbk_Formulario1_CuadroCombinado1))
  (setq bksel3(dcl_ComboBox_GetLBText estbk_Formulario1_CuadroCombinado1 bksel1))
    (f:selfilt)
)

(defun c:estbk_Formulario1_BotonOpcion1_OnAccionado (Value /)
  (dcl_Control_SetEnabled estbk_Formulario1_Grid1 T)
  (dcl_Grid_Clear estbk_Formulario1_Grid1)
  (dcl_Control_SetEnabled estbk_Formulario1_Marco1 T)
  (dcl_Control_SetCaption estbk_Formulario1_Marco1 "Leyes de Mina -> LEYCOPMC")
    (setq opttp 1)
    (rellgrid)
    
)

(defun c:estbk_Formulario1_BotonOpcion3_OnAccionado (Value /)
  (dcl_Control_SetEnabled estbk_Formulario1_Grid1 T)
  (dcl_Grid_Clear estbk_Formulario1_Grid1)
  (dcl_Control_SetEnabled estbk_Formulario1_Marco1 T)
  (dcl_Control_SetCaption estbk_Formulario1_Marco1 "Leyes de Mina -> LEYCOPMV")
    (setq opttp 3)
    (rellgrid)
)


(defun c:estbk_Formulario1_BotonOpcion2_OnAccionado (Value /)
  (dcl_Control_SetEnabled estbk_Formulario1_Grid1 T)
  (dcl_Grid_Clear estbk_Formulario1_Grid1)
  (dcl_Control_SetEnabled estbk_Formulario1_Marco1 T)
  (dcl_Control_SetCaption estbk_Formulario1_Marco1 "Leyes de Tajo -> LEYCOPT")
    (setq opttp 2)
    (rellgrid)
    
)

;;;(defun c:estbk_Formulario1_BotónGráfico3_OnAccionado (/)
;;;  (dcl_Form_Close estbk_Formulario1)
;;;)

(defun c:estbk_Formulario1_OnCancelarCerrar (Reason / DIAOLOGO)
    (if (= REASON 1)
   (setq DIALOGO 1)
   (setq DIALOGO 1)
      )
    )

(defun c:estbk_Formulario1_BotónGráfico4_OnAccionado (/)
  (dcl_Form_Close estbk_Formulario1)
)


(defun c:estbk_Formulario1_BotónGráfico3_OnAccionado (/)

 (if (or (= bksel3 "Muestras")(= bksel3 "MuestrasTj"))
     (progn     
     (setq countaut 0)
     (repeat (length tittag)
     (setq namrellaut(nth countaut (reverse tittag)))
     (dcl_Grid_SetCellText estbk_Formulario1_Grid1 countaut 1 namrellaut)
         (setq countaut(+ 1 countaut))
         )
     )
  (dcl_MessageBox "El bloque seleccionado no fue ploteado del Sistema de Operaciones")
)
    )


(DEFUN cnterr (CadenaError)
(SETQ *error* error0)
(IF (= CadenaError "Function cancelled")
    (progn
        (dcl_Form_Close estbk_Formulario1)
(PROMPT "La función ha sido interrumpida por el usuario."))
)
(TERPRI)
(PRIN1)
) 



(defun f:namtag()

    (SETQ error0 *error* *error* cnterr)
    
    (setq blox (ssget '((66 . 1))))

                (if (= blox nil)
                (progn
                  (alert "No selecciono bloques con atributos!")
                  (dcl_Form_show estbk_Formulario1)
                  (exit)
                  )
         )
    
    (setq n 0)
    (setq listtag nil)
    (repeat (sslength blox)
        (setq entins (ssname blox n))
        (setq entblk (entget entins))
        (setq namblk (cdr (assoc 2 entblk)))
        (setq perono (member namblk listtag))
        (if (= perono nil)
            (setq listtag (cons namblk listtag))
            )
        (setq n (+ 1 n))
        )
(if (/= blox nil)
    (dcl_ComboBox_AddList estbk_Formulario1_CuadroCombinado1 listtag)
    )
    )

(defun f:selfilt ()
    (SETQ error0 *error* *error* cnterr)
       
       (setq bloxfl (ssget "P" (list (cons 2 bksel3))))
       (setq bloxf2 (sslength bloxfl))(setq nq 0)

(repeat 1
        (setq entins1 (ssname bloxfl nq))
        (setq entatt1 entins1)
        (setq lstattsins nil)
        (setq tittag nil)
        (while
            (= (cdr (assoc 0
                           (setq lent (entget (setq entatt1 (entnext entatt1))))
                    )
               )
               "ATTRIB"
            )  ;; comprobar el primer attributo del bloque si tiene data attrib
               (setq tag (cdr (assoc 2 lent)))
               ;;extrae el nombre del ATTRIB
               (setq val (cdr (assoc 1 lent)))
               ;;extrae el valor de ATTRIB
               (setq lstattsins (cons (list tag val) lstattsins))
               ;;formar lista con el nombre y el valor de atributo
               (setq tittag (cons tag tittag))
            )    
    )
)
    
(defun rellgrid ()  

    (if (or (= opttp 1)(= opttp 3))
        (progn
    	(dcl_Grid_AddString estbk_Formulario1_Grid1 "Canal")
        (dcl_Grid_AddString estbk_Formulario1_Grid1 "ID")
        (dcl_Grid_AddString estbk_Formulario1_Grid1 "Muestra")
        (dcl_Grid_AddString estbk_Formulario1_Grid1 "Fecha")
        (dcl_Grid_AddString estbk_Formulario1_Grid1 "Este")
        (dcl_Grid_AddString estbk_Formulario1_Grid1 "Norte")
        (dcl_Grid_AddString estbk_Formulario1_Grid1 "Cota")
        (dcl_Grid_AddString estbk_Formulario1_Grid1 "Azimut")
        (dcl_Grid_AddString estbk_Formulario1_Grid1 "Angulo")
	(dcl_Grid_AddString estbk_Formulario1_Grid1 "Alt.Muest.")
        (dcl_Grid_AddString estbk_Formulario1_Grid1 "A.Muestra")
        (dcl_Grid_AddString estbk_Formulario1_Grid1 "A.Labor")
        (dcl_Grid_AddString estbk_Formulario1_Grid1 "Cobre")
        (dcl_Grid_AddString estbk_Formulario1_Grid1 "Plomo")
        (dcl_Grid_AddString estbk_Formulario1_Grid1 "Zinc")
        (dcl_Grid_AddString estbk_Formulario1_Grid1 "Plata")
        (dcl_Grid_AddString estbk_Formulario1_Grid1 "Oro")
        (dcl_Grid_AddString estbk_Formulario1_Grid1 "Fierro")
        (dcl_Grid_AddString estbk_Formulario1_Grid1 "Arsenico")
        (dcl_Grid_AddString estbk_Formulario1_Grid1 "Antimonio")
        (dcl_Grid_AddString estbk_Formulario1_Grid1 "Bismuto")
        (dcl_Grid_AddString estbk_Formulario1_Grid1 "Volframio")
        (dcl_Grid_AddString estbk_Formulario1_Grid1 "Niquel")
        (dcl_Grid_AddString estbk_Formulario1_Grid1 "Cobalto")
        (dcl_Grid_AddString estbk_Formulario1_Grid1 "Oxido Plomo")
        (dcl_Grid_AddString estbk_Formulario1_Grid1 "Oxido Zinc")
        (dcl_Grid_AddString estbk_Formulario1_Grid1 "Insoluble")
        (setq nred 0)
	(repeat 27
            (dcl_Grid_SetItemStyle estbk_Formulario1_Grid1 nred 1 18)
            (dcl_Grid_SetItemDropList estbk_Formulario1_Grid1
							  nred 1
							   (reverse (append (list "")tittag)))
            (setq nred(+ 1 nred))
        )
        )
        
        (progn
        (dcl_Grid_AddString estbk_Formulario1_Grid1 "ID")
        (dcl_Grid_AddString estbk_Formulario1_Grid1 "Muestra")
        (dcl_Grid_AddString estbk_Formulario1_Grid1 "Fecha")
        (dcl_Grid_AddString estbk_Formulario1_Grid1 "Este")
        (dcl_Grid_AddString estbk_Formulario1_Grid1 "Norte")
        (dcl_Grid_AddString estbk_Formulario1_Grid1 "Cota")
        (dcl_Grid_AddString estbk_Formulario1_Grid1 "Azimut")
        (dcl_Grid_AddString estbk_Formulario1_Grid1 "Angulo")
	(dcl_Grid_AddString estbk_Formulario1_Grid1 "Alt-Bh")       
        (dcl_Grid_AddString estbk_Formulario1_Grid1 "Cobre")
        (dcl_Grid_AddString estbk_Formulario1_Grid1 "Plomo")
        (dcl_Grid_AddString estbk_Formulario1_Grid1 "Zinc")
        (dcl_Grid_AddString estbk_Formulario1_Grid1 "Plata")
        (dcl_Grid_AddString estbk_Formulario1_Grid1 "Oro")
        (dcl_Grid_AddString estbk_Formulario1_Grid1 "Fierro")
        (dcl_Grid_AddString estbk_Formulario1_Grid1 "Arsenico")
        (dcl_Grid_AddString estbk_Formulario1_Grid1 "Antimonio")
        (dcl_Grid_AddString estbk_Formulario1_Grid1 "Bismuto")
        (dcl_Grid_AddString estbk_Formulario1_Grid1 "Volframio")
        (dcl_Grid_AddString estbk_Formulario1_Grid1 "Niquel")
        (dcl_Grid_AddString estbk_Formulario1_Grid1 "Cobalto")
        (dcl_Grid_AddString estbk_Formulario1_Grid1 "Oxido Plomo")
        (dcl_Grid_AddString estbk_Formulario1_Grid1 "Oxido Zinc")
        (dcl_Grid_AddString estbk_Formulario1_Grid1 "Insoluble")

        (setq nred 0)
        (repeat 24
            (dcl_Grid_SetItemStyle estbk_Formulario1_Grid1 nred 1 18)
            (dcl_Grid_SetItemDropList estbk_Formulario1_Grid1
							  nred 1
							   (reverse (append (list "")tittag)))
            (setq nred(+ 1 nred))
        )
        )
        )
    )

(defun c:estbk_Formulario1_BotónGráfico2_OnAccionado (/)
  (setq opt1sel(dcl_Control_GetValue estbk_Formulario1_BotonOpcion1))
  (setq opt3sel(dcl_Control_GetValue estbk_Formulario1_BotonOpcion3))
  (setq opt2sel(dcl_Control_GetValue estbk_Formulario1_BotonOpcion2))
    (COMMAND "_-STYLE" "STBKCOR" "SIMPLEX" "" "" "" "" "" "" )
    (if (and (= opt1sel 1)(= (tblsearch "BLOCK" "LEYCORPMC") nil))
        (genbkmnc)
        )
    (if (and (= opt3sel 1)(= (tblsearch "BLOCK" "LEYCORPMV") nil))
        (genbkmnv)
        )
    (if (and (= opt2sel 1)(= (tblsearch "BLOCK" "LEYCORPT") nil))
        (genbktj)
        )
  (setq datcolm(dcl_Grid_GetColumnCells estbk_Formulario1_Grid1 1))
    (if
        (or (equal datcolm (list "" "" "" "" "" "" "" "" "" "" "" "" "" "" "" "" "" "" "" "" "" "" "" "" "" "" ""))
            (equal datcolm (list "" "" "" "" "" "" "" "" "" "" "" "" "" "" "" "" "" "" "" "" "" "" "" ""))
            )
        (dcl_MessageBox "Los Campos de la columna Bloques no fueron definidos" "" 2)
        (f:reemplz)
        )
    )

(defun f:reemplz()

  (command "ucsicon" "off")
  (command "ucs" "w")

    (SETQ error0 *error* *error* cnterr)
        
(setq bloxf2 (sslength bloxfl))(setq nq 0)
(repeat bloxf2
(setq entins1 (ssname bloxfl nq))
        		 (setq entatt1 entins1)
		         (setq lstattsins nil)
		         (setq tittag nil)
    			 (setq coord (trans (cdr (assoc 10 (entget entins1)))0 1))
    			 (setq blklaye (cdr (assoc 8 (entget entins1))))
    			 (COMMAND "_-LAYER" "M" blklaye "")
    			 (setq xpt (car coord))
	   		 (setq ypt (cadr coord))
		    	 (setq zpt (caddr coord))
		        (while
		            (= (cdr (assoc 0
		                           (setq lent (entget (setq entatt1 (entnext entatt1))))
		                    )
		               )
		               "ATTRIB"
		            )  ;; comprobar el primer attributo del bloque si tiene data attrib
                               (setq rttag (assoc 50 lent))
		               (setq tag (cdr (assoc 2 lent)))
		               ;;extrae el nombre del ATTRIB
		               (setq val (cdr (assoc 1 lent)))
		               ;;extrae el valor de ATTRIB
		               (setq lstattsins (cons (list tag val) lstattsins))
		               ;;formar lista con el nombre y el valor de atributo
		               (setq tittag (cons tag tittag))
		            )
 (setq contcold 0)
 (setq valtag nil)
 (setq idcampdat (length datcolm))
    (repeat idcampdat
    (setq nombar(nth contcold datcolm))
      (if (equal nombar "")
        (progn
        (setq nam1 "")
        (setq valtag (cons nam1 valtag))
        (setq contcold (+ 1 contcold))
        )
        (progn
        (setq nam1 (cadr (assoc nombar lstattsins)))
	(if (>= contcold 8)
	  (progn
	    	(setq vardmz (getvar "dimzin"))
		(setvar "dimzin" (logand vardmz (~ 8))) ;desactivar el bit de supresion de cero a la derecha
	    	(setq nam1(rtos (atof nam1)2 2))
	    (setvar "dimzin" vardmz)
	    ))
	
        (setq valtag (cons nam1 valtag))

        (setq contcold (+ 1 contcold))
        )
          )
        )
	(setq plotnw (reverse valtag))

    (cond ((= opttp 1)(setq namgen "LEYCORPMC"))
          ((= opttp 3)(setq namgen "LEYCORPMV"))
          ((= opttp 2)(setq namgen "LEYCORPT"))
          )
        
       (setq angrt(angtos (cdr rttag)0 7))
    
    	(vl-cmdf "_-insert" namgen "R" angrt (list xpt ypt zpt) "" "")
        (mapcar 'command plotnw)

    (entdel entins1)
    
    (setq nq (+ 1 nq))
)

  (command "ucs" "p")
  (command "ucsicon" "on")
    
    )


(defun genbkmnc ()                                ;crear el bloque 'punto' solo si no existe
            (entmake '((0 . "BLOCK")
                       (8 . "0")
                       (10 0.0 0.0 0.0)
                       (2 . "LEYCORPMC")
                       (70 . 2)
                      )
            )                                     ;la entidad punto
            (entmake '((0 . "CIRCLE")
                       (67 . 0)
                       (8 . "0")
                       (10 0.0 0.0 0.0)
                       (40 . 0.1)
                       (370 . 15)
                       (210 0.0 0.0 1.0)
                       (100 . "AcDbEntity")
                       (100 . "AcDbCircle")
                      )
            )                                     ;el atributo número de punto
            (entmake '((0 . "ATTDEF")
                       (8 . "0")
                       (10 0.4 -1.0 0.0)
                       (1 . "")
                       (7 . "STBKCOR")
                       (2 . "Canal")
                       (3 . "Canal")
                       (40 . 0.8)
                       (41 . 0.8)
                       (50 . 0.0)
                       (70 . 1)
                       (71 . 0)
                       (72 . 0)
                       (73 . 2)
                      )
            )                                     ;el atributo cota
            (entmake '((0 . "ATTDEF")
                       (8 . "0")
                       (10 0.4 0.0 0.0)
                       (1 . "")
                       (7 . "STBKCOR")
                       (2 . "ID")
                       (3 . "ID")
                       (40 . 0.8)
                       (41 . 0.8)
                       (50 . 0.0)
                       (70 . 0)
                       (71 . 0)
                       (72 . 0)
                       (73 . 2)
                      )
            )
            (entmake '((0 . "ATTDEF")
                       (8 . "0")
                       (10 0.4 1.0 0.0)
                       (1 . "")
                       (7 . "STBKCOR")
                       (2 . "Muestra")
                       (3 . "Muestra")
                       (40 . 0.8)
                       (41 . 0.8)
                       (50 . 0.0)
                       (70 . 1)
                       (71 . 0)
                       (72 . 0)
                       (73 . 2)
                      )
            )
            (entmake '((0 . "ATTDEF")
                       (8 . "0")
                       (10 0.4 2.0 0.0)
                       (1 . "")
                       (7 . "STBKCOR")
                       (2 . "Fecha")
                       (3 . "Fecha")
                       (40 . 0.8)
                       (41 . 0.8)
                       (50 . 0.0)
                       (70 . 1)
                       (71 . 0)
                       (72 . 0)
                       (73 . 2)
                      )
            )
                (entmake '((0 . "ATTDEF")
                       (8 . "0")
                       (10 0.4 21.0 0.0)
                       (1 . "")
                       (7 . "STBKCOR")
                       (2 . "Este")
                       (3 . "ESTE")
                       (40 . 0.8)
                       (41 . 0.8)
                       (50 . 0.0)
                       (70 . 1)
                       (71 . 0)
                       (72 . 0)
                       (73 . 2)
                      )
            )
            (entmake '((0 . "ATTDEF")
                       (8 . "0")
                       (10 0.4 22.0 0.0)
                       (1 . "")
                       (7 . "STBKCOR")
                       (2 . "Norte")
                       (3 . "NORTE")
                       (40 . 0.8)
                       (41 . 0.8)
                       (50 . 0.0)
                       (70 . 1)
                       (71 . 0)
                       (72 . 0)
                       (73 . 2)
                      )
            )
            (entmake '((0 . "ATTDEF")
                       (8 . "0")
                       (10 0.4 23.0 0.0)
                       (1 . "")
                       (7 . "STBKCOR")
                       (2 . "Cota")
                       (3 . "COTA")
                       (40 . 0.8)
                       (41 . 0.8)
                       (50 . 0.0)
                       (70 . 1)
                       (71 . 0)
                       (72 . 0)
                       (73 . 2)
                      )
            )
            (entmake '((0 . "ATTDEF")
                       (8 . "0")
                       (10 0.4 24.0 0.0)
                       (1 . "")
                       (7 . "STBKCOR")
                       (2 . "Azimut")
                       (3 . "AZIMUT")
                       (40 . 0.8)
                       (41 . 0.8)
                       (50 . 0.0)
                       (70 . 1)
                       (71 . 0)
                       (72 . 0)
                       (73 . 2)
                      )
            )
            (entmake '((0 . "ATTDEF")
                       (8 . "0")
                       (10 0.4 25.0 0.0)
                       (1 . "")
                       (7 . "STBKCOR")
                       (2 . "Angulo")
                       (3 . "ANG")
                       (40 . 0.8)
                       (41 . 0.8)
                       (50 . 0.0)
                       (70 . 1)
                       (71 . 0)
                       (72 . 0)
                       (73 . 2)
                      )
            )  
            (entmake '((0 . "ATTDEF")
                       (8 . "0")
                       (10 0.4 3.0 0.0)
                       (1 . "")
                       (7 . "STBKCOR")
                       (2 . "Alt.Muestra")
                       (3 . "Alt.M.")
                       (40 . 0.8)
                       (41 . 0.8)
                       (50 . 0.0)
                       (70 . 1)
                       (71 . 0)
                       (72 . 0)
                       (73 . 2)
                      )
            )
            (entmake '((0 . "ATTDEF")
                       (8 . "0")
                       (10 0.4 4.0 0.0)
                       (1 . "")
                       (7 . "STBKCOR")
                       (2 . "A.Muestra")
                       (3 . "Am.")
                       (40 . 0.8)
                       (41 . 0.8)
                       (50 . 0.0)
                       (70 . 1)
                       (71 . 0)
                       (72 . 0)
                       (73 . 2)
                      )
            )
            (entmake '((0 . "ATTDEF")
                       (8 . "0")
                       (10 0.4 5.0 0.0)
                       (1 . "")
                       (7 . "STBKCOR")
                       (2 . "A.Labor")
                       (3 . "Al.")
                       (40 . 0.8)
                       (41 . 0.8)
                       (50 . 0.0)
                       (70 . 1)
                       (71 . 0)
                       (72 . 0)
                       (73 . 2)
                      )
            )
            (entmake '((0 . "ATTDEF")
                       (8 . "0")
                       (10 0.4 6.0 0.0)
                       (1 . "")
                       (7 . "STBKCOR")
                       (2 . "Cobre")
                       (3 . "%Cu")
                       (40 . 0.8)
                       (41 . 0.8)
                       (50 . 0.0)
                       (70 . 1)
                       (71 . 0)
                       (72 . 0)
                       (73 . 2)
                      )
            )
            (entmake '((0 . "ATTDEF")
                       (8 . "0")
                       (10 0.4 7.0 0.0)
                       (1 . "")
                       (7 . "STBKCOR")
                       (2 . "Plomo")
                       (3 . "%Pb")
                       (40 . 0.8)
                       (41 . 0.8)
                       (50 . 0.0)
                       (70 . 1)
                       (71 . 0)
                       (72 . 0)
                       (73 . 2)
                      )
            )
            (entmake '((0 . "ATTDEF")
                       (8 . "0")
                       (10 0.4 8.0 0.0)
                       (1 . "")
                       (7 . "STBKCOR")
                       (2 . "Zinc")
                       (3 . "%Zn")
                       (40 . 0.8)
                       (41 . 0.8)
                       (50 . 0.0)
                       (70 . 1)
                       (71 . 0)
                       (72 . 0)
                       (73 . 2)
                      )
            )
            (entmake '((0 . "ATTDEF")
                       (8 . "0")
                       (10 0.4 9.0 0.0)
                       (1 . "")
                       (7 . "STBKCOR")
                       (2 . "Plata")
                       (3 . "OzAg")
                       (40 . 0.8)
                       (41 . 0.8)
                       (50 . 0.0)
                       (70 . 1)
                       (71 . 0)
                       (72 . 0)
                       (73 . 2)
                      )
            )
            (entmake '((0 . "ATTDEF")
                       (8 . "0")
                       (10 0.4 10.0 0.0)
                       (1 . "")
                       (7 . "STBKCOR")
                       (2 . "Oro")
                       (3 . "GrAu")
                       (40 . 0.8)
                       (41 . 0.8)
                       (50 . 0.0)
                       (70 . 1)
                       (71 . 0)
                       (72 . 0)
                       (73 . 2)
                      )
            )
            (entmake '((0 . "ATTDEF")
                       (8 . "0")
                       (10 0.4 11.0 0.0)
                       (1 . "")
                       (7 . "STBKCOR")
                       (2 . "Fierro")
                       (3 . "%Fe")
                       (40 . 0.8)
                       (41 . 0.8)
                       (50 . 0.0)
                       (70 . 1)
                       (71 . 0)
                       (72 . 0)
                       (73 . 2)
                      )
            )
            (entmake '((0 . "ATTDEF")
                       (8 . "0")
                       (10 0.4 12.0 0.0)
                       (1 . "")
                       (7 . "STBKCOR")
                       (2 . "Arsenico")
                       (3 . "%As")
                       (40 . 0.8)
                       (41 . 0.8)
                       (50 . 0.0)
                       (70 . 1)
                       (71 . 0)
                       (72 . 0)
                       (73 . 2)
                      )
            )
            (entmake '((0 . "ATTDEF")
                       (8 . "0")
                       (10 0.4 13.0 0.0)
                       (1 . "")
                       (7 . "STBKCOR")
                       (2 . "Antimonio")
                       (3 . "%Sb")
                       (40 . 0.8)
                       (41 . 0.8)
                       (50 . 0.0)
                       (70 . 1)
                       (71 . 0)
                       (72 . 0)
                       (73 . 2)
                      )
            )
            (entmake '((0 . "ATTDEF")
                       (8 . "0")
                       (10 0.4 14.0 0.0)
                       (1 . "")
                       (7 . "STBKCOR")
                       (2 . "Bismuto")
                       (3 . "%Bi")
                       (40 . 0.8)
                       (41 . 0.8)
                       (50 . 0.0)
                       (70 . 1)
                       (71 . 0)
                       (72 . 0)
                       (73 . 2)
                      )
            )
            (entmake '((0 . "ATTDEF")
                       (8 . "0")
                       (10 0.4 15.0 0.0)
                       (1 . "")
                       (7 . "STBKCOR")
                       (2 . "Volframio")
                       (3 . "%W")
                       (40 . 0.8)
                       (41 . 0.8)
                       (50 . 0.0)
                       (70 . 1)
                       (71 . 0)
                       (72 . 0)
                       (73 . 2)
                      )
            )
            (entmake '((0 . "ATTDEF")
                       (8 . "0")
                       (10 0.4 16.0 0.0)
                       (1 . "")
                       (7 . "STBKCOR")
                       (2 . "Niquel")
                       (3 . "%Ni")
                       (40 . 0.8)
                       (41 . 0.8)
                       (50 . 0.0)
                       (70 . 1)
                       (71 . 0)
                       (72 . 0)
                       (73 . 2)
                      )
            )
            (entmake '((0 . "ATTDEF")
                       (8 . "0")
                       (10 0.4 17.0 0.0)
                       (1 . "")
                       (7 . "STBKCOR")
                       (2 . "Cobalto")
                       (3 . "%Co")
                       (40 . 0.8)
                       (41 . 0.8)
                       (50 . 0.0)
                       (70 . 1)
                       (71 . 0)
                       (72 . 0)
                       (73 . 2)
                      )
            )
            (entmake '((0 . "ATTDEF")
                       (8 . "0")
                       (10 0.4 18.0 0.0)
                       (1 . "")
                       (7 . "STBKCOR")
                       (2 . "Oxido_Plomo")
                       (3 . "OxPb")
                       (40 . 0.8)
                       (41 . 0.8)
                       (50 . 0.0)
                       (70 . 1)
                       (71 . 0)
                       (72 . 0)
                       (73 . 2)
                      )
            )
            (entmake '((0 . "ATTDEF")
                       (8 . "0")
                       (10 0.4 19.0 0.0)
                       (1 . "")
                       (7 . "STBKCOR")
                       (2 . "Oxido_Zinc")
                       (3 . "OxZn")
                       (40 . 0.8)
                       (41 . 0.8)
                       (50 . 0.0)
                       (70 . 1)
                       (71 . 0)
                       (72 . 0)
                       (73 . 2)
                      )
            )
            (entmake '((0 . "ATTDEF")
                       (8 . "0")
                       (10 0.4 20.0 0.0)
                       (1 . "")
                       (7 . "STBKCOR")
                       (2 . "Insoluble")
                       (3 . "Ins.")
                       (40 . 0.8)
                       (41 . 0.8)
                       (50 . 0.0)
                       (70 . 1)
                       (71 . 0)
                       (72 . 0)
                       (73 . 2)
                      )
            )
                                   ;final del bloque
            (entmake '((0 . "ENDBLK")))
;;;        )
;;;    )
)

(defun genbktj ()                                ;crear el bloque 'punto' solo si no existe
;;;    (if (= (tblsearch "BLOCK" "LEYCORP") nil)
;;;        (progn                                    ;definición del bloque
            (entmake '((0 . "BLOCK")
                       (8 . "0")
                       (10 0.0 0.0 0.0)
                       (2 . "LEYCORPT")
                       (70 . 2)
                      )
            )                                     ;la entidad punto
            (entmake '((0 . "CIRCLE")
                       (67 . 0)
                       (8 . "0")
                       (10 0.0 0.0 0.0)
                       (40 . 0.1)
                       (370 . 15)
                       (210 0.0 0.0 1.0)
                       (100 . "AcDbEntity")
                       (100 . "AcDbCircle")
                      )
            )                                     ;el atributo número de punto
            (entmake '((0 . "ATTDEF")
                       (8 . "0")
                       (10 0.4 0.0 0.0)
                       (1 . "")
                       (7 . "STBKCOR")
                       (2 . "ID")
                       (3 . "ID")
                       (40 . 0.8)
                       (41 . 0.8)
                       (50 . 0.0)
                       (70 . 0)
                       (71 . 0)
                       (72 . 0)
                       (73 . 2)
                      )
            )   
            (entmake '((0 . "ATTDEF")
                       (8 . "0")
                       (10 0.4 1.0 0.0)
                       (1 . "")
                       (7 . "STBKCOR")
                       (2 . "Muestra")
                       (3 . "Muestra")
                       (40 . 0.8)
                       (41 . 0.8)
                       (50 . 0.0)
                       (70 . 1)
                       (71 . 0)
                       (72 . 0)
                       (73 . 2)
                      )
            )
            (entmake '((0 . "ATTDEF")
                       (8 . "0")
                       (10 0.4 2.0 0.0)
                       (1 . "")
                       (7 . "STBKCOR")
                       (2 . "Fecha")
                       (3 . "Fecha")
                       (40 . 0.8)
                       (41 . 0.8)
                       (50 . 0.0)
                       (70 . 1)
                       (71 . 0)
                       (72 . 0)
                       (73 . 2)
                      )
            )
    (entmake '((0 . "ATTDEF")
                       (8 . "0")
                       (10 0.4 24.0 0.0)
                       (1 . "")
                       (7 . "STBKCOR")
                       (2 . "Este")
                       (3 . "ESTE")
                       (40 . 0.8)
                       (41 . 0.8)
                       (50 . 0.0)
                       (70 . 1)
                       (71 . 0)
                       (72 . 0)
                       (73 . 2)
                      )
            )
            (entmake '((0 . "ATTDEF")
                       (8 . "0")
                       (10 0.4 25.0 0.0)
                       (1 . "")
                       (7 . "STBKCOR")
                       (2 . "Norte")
                       (3 . "NORTE")
                       (40 . 0.8)
                       (41 . 0.8)
                       (50 . 0.0)
                       (70 . 1)
                       (71 . 0)
                       (72 . 0)
                       (73 . 2)
                      )
            )
            (entmake '((0 . "ATTDEF")
                       (8 . "0")
                       (10 0.4 26.0 0.0)
                       (1 . "")
                       (7 . "STBKCOR")
                       (2 . "Cota")
                       (3 . "COTA")
                       (40 . 0.8)
                       (41 . 0.8)
                       (50 . 0.0)
                       (70 . 1)
                       (71 . 0)
                       (72 . 0)
                       (73 . 2)
                      )
            )
            (entmake '((0 . "ATTDEF")
                       (8 . "0")
                       (10 0.4 27.0 0.0)
                       (1 . "")
                       (7 . "STBKCOR")
                       (2 . "Azimut")
                       (3 . "AZIMUT")
                       (40 . 0.8)
                       (41 . 0.8)
                       (50 . 0.0)
                       (70 . 1)
                       (71 . 0)
                       (72 . 0)
                       (73 . 2)
                      )
            )
            (entmake '((0 . "ATTDEF")
                       (8 . "0")
                       (10 0.4 28.0 0.0)
                       (1 . "")
                       (7 . "STBKCOR")
                       (2 . "Angulo")
                       (3 . "ANG")
                       (40 . 0.8)
                       (41 . 0.8)
                       (50 . 0.0)
                       (70 . 1)
                       (71 . 0)
                       (72 . 0)
                       (73 . 2)
                      )
            )
            (entmake '((0 . "ATTDEF")
                       (8 . "0")
                       (10 0.4 3.0 0.0)
                       (1 . "")
                       (7 . "STBKCOR")
                       (2 . "Alt-Bh")
                       (3 . "Alt-Bh")
                       (40 . 0.8)
                       (41 . 0.8)
                       (50 . 0.0)
                       (70 . 1)
                       (71 . 0)
                       (72 . 0)
                       (73 . 2)
                      )
            )
            (entmake '((0 . "ATTDEF")
                       (8 . "0")
                       (10 0.4 6.0 0.0)
                       (1 . "")
                       (7 . "STBKCOR")
                       (2 . "Cobre")
                       (3 . "%Cu")
                       (40 . 0.8)
                       (41 . 0.8)
                       (50 . 0.0)
                       (70 . 1)
                       (71 . 0)
                       (72 . 0)
                       (73 . 2)
                      )
            )
            (entmake '((0 . "ATTDEF")
                       (8 . "0")
                       (10 0.4 7.0 0.0)
                       (1 . "")
                       (7 . "STBKCOR")
                       (2 . "Plomo")
                       (3 . "%Pb")
                       (40 . 0.8)
                       (41 . 0.8)
                       (50 . 0.0)
                       (70 . 1)
                       (71 . 0)
                       (72 . 0)
                       (73 . 2)
                      )
            )
            (entmake '((0 . "ATTDEF")
                       (8 . "0")
                       (10 0.4 8.0 0.0)
                       (1 . "")
                       (7 . "STBKCOR")
                       (2 . "Zinc")
                       (3 . "%Zn")
                       (40 . 0.8)
                       (41 . 0.8)
                       (50 . 0.0)
                       (70 . 1)
                       (71 . 0)
                       (72 . 0)
                       (73 . 2)
                      )
            )
            (entmake '((0 . "ATTDEF")
                       (8 . "0")
                       (10 0.4 9.0 0.0)
                       (1 . "")
                       (7 . "STBKCOR")
                       (2 . "Plata")
                       (3 . "OzAg")
                       (40 . 0.8)
                       (41 . 0.8)
                       (50 . 0.0)
                       (70 . 1)
                       (71 . 0)
                       (72 . 0)
                       (73 . 2)
                      )
            )
            (entmake '((0 . "ATTDEF")
                       (8 . "0")
                       (10 0.4 10.0 0.0)
                       (1 . "")
                       (7 . "STBKCOR")
                       (2 . "Oro")
                       (3 . "GrAu")
                       (40 . 0.8)
                       (41 . 0.8)
                       (50 . 0.0)
                       (70 . 1)
                       (71 . 0)
                       (72 . 0)
                       (73 . 2)
                      )
            )
            (entmake '((0 . "ATTDEF")
                       (8 . "0")
                       (10 0.4 11.0 0.0)
                       (1 . "")
                       (7 . "STBKCOR")
                       (2 . "Fierro")
                       (3 . "%Fe")
                       (40 . 0.8)
                       (41 . 0.8)
                       (50 . 0.0)
                       (70 . 1)
                       (71 . 0)
                       (72 . 0)
                       (73 . 2)
                      )
            )
            (entmake '((0 . "ATTDEF")
                       (8 . "0")
                       (10 0.4 12.0 0.0)
                       (1 . "")
                       (7 . "STBKCOR")
                       (2 . "Arsenico")
                       (3 . "%As")
                       (40 . 0.8)
                       (41 . 0.8)
                       (50 . 0.0)
                       (70 . 1)
                       (71 . 0)
                       (72 . 0)
                       (73 . 2)
                      )
            )
            (entmake '((0 . "ATTDEF")
                       (8 . "0")
                       (10 0.4 13.0 0.0)
                       (1 . "")
                       (7 . "STBKCOR")
                       (2 . "Antimonio")
                       (3 . "%Sb")
                       (40 . 0.8)
                       (41 . 0.8)
                       (50 . 0.0)
                       (70 . 1)
                       (71 . 0)
                       (72 . 0)
                       (73 . 2)
                      )
            )
            (entmake '((0 . "ATTDEF")
                       (8 . "0")
                       (10 0.4 14.0 0.0)
                       (1 . "")
                       (7 . "STBKCOR")
                       (2 . "Bismuto")
                       (3 . "%Bi")
                       (40 . 0.8)
                       (41 . 0.8)
                       (50 . 0.0)
                       (70 . 1)
                       (71 . 0)
                       (72 . 0)
                       (73 . 2)
                      )
            )
            (entmake '((0 . "ATTDEF")
                       (8 . "0")
                       (10 0.4 15.0 0.0)
                       (1 . "")
                       (7 . "STBKCOR")
                       (2 . "Volframio")
                       (3 . "%W")
                       (40 . 0.8)
                       (41 . 0.8)
                       (50 . 0.0)
                       (70 . 1)
                       (71 . 0)
                       (72 . 0)
                       (73 . 2)
                      )
            )
            (entmake '((0 . "ATTDEF")
                       (8 . "0")
                       (10 0.4 16.0 0.0)
                       (1 . "")
                       (7 . "STBKCOR")
                       (2 . "Niquel")
                       (3 . "%Ni")
                       (40 . 0.8)
                       (41 . 0.8)
                       (50 . 0.0)
                       (70 . 1)
                       (71 . 0)
                       (72 . 0)
                       (73 . 2)
                      )
            )
            (entmake '((0 . "ATTDEF")
                       (8 . "0")
                       (10 0.4 17.0 0.0)
                       (1 . "")
                       (7 . "STBKCOR")
                       (2 . "Cobalto")
                       (3 . "%Co")
                       (40 . 0.8)
                       (41 . 0.8)
                       (50 . 0.0)
                       (70 . 1)
                       (71 . 0)
                       (72 . 0)
                       (73 . 2)
                      )
            )
            (entmake '((0 . "ATTDEF")
                       (8 . "0")
                       (10 0.4 18.0 0.0)
                       (1 . "")
                       (7 . "STBKCOR")
                       (2 . "Oxido_Plomo")
                       (3 . "OxPb")
                       (40 . 0.8)
                       (41 . 0.8)
                       (50 . 0.0)
                       (70 . 1)
                       (71 . 0)
                       (72 . 0)
                       (73 . 2)
                      )
            )
            (entmake '((0 . "ATTDEF")
                       (8 . "0")
                       (10 0.4 19.0 0.0)
                       (1 . "")
                       (7 . "STBKCOR")
                       (2 . "Oxido_Zinc")
                       (3 . "OxZn")
                       (40 . 0.8)
                       (41 . 0.8)
                       (50 . 0.0)
                       (70 . 1)
                       (71 . 0)
                       (72 . 0)
                       (73 . 2)
                      )
            )
            (entmake '((0 . "ATTDEF")
                       (8 . "0")
                       (10 0.4 20.0 0.0)
                       (1 . "")
                       (7 . "STBKCOR")
                       (2 . "Insoluble")
                       (3 . "Ins.")
                       (40 . 0.8)
                       (41 . 0.8)
                       (50 . 0.0)
                       (70 . 1)
                       (71 . 0)
                       (72 . 0)
                       (73 . 2)
                      )
            )
                                                 ;final del bloque
            (entmake '((0 . "ENDBLK")))
;;;        )
;;;    )
)


(defun genbkmnv ()                                ;crear el bloque 'punto' solo si no existe
            (entmake '((0 . "BLOCK")
                       (8 . "0")
                       (10 0.0 0.0 0.0)
                       (2 . "LEYCORPMV")
                       (70 . 2)
                      )
            )                                     ;la entidad punto
            (entmake '((0 . "CIRCLE")
                       (67 . 0)
                       (8 . "0")
                       (10 0.0 0.0 0.0)
                       (40 . 0.1)
                       (370 . 15)
                       (210 0.0 0.0 1.0)
                       (100 . "AcDbEntity")
                       (100 . "AcDbCircle")
                      )
            )                                     ;el atributo número de punto

    	   (entmake '((0 . "LINE")
                       (8 . "0")
                       (10 0.0 0.0 0.0)
                       (11 10.0 0.0 0.0)
                       (210 0.0 0.0 1.0)
                       (100 . "AcDbEntity")
                       (100 . "AcDbLine")
                      )
            )    
            (entmake '((0 . "ATTDEF")
                       (8 . "0")
                       (10 0.5 0.0 0.0)
                       (11 0.5 0.0 0.0)
                       (1 . "")
                       (7 . "STBKCOR")
                       (2 . "Canal")
                       (3 . "Canal")
                       (40 . 1.2)
                       (41 . 0.8)
                       (50 . 0.0)
                       (70 . 1)
                       (71 . 0)
                       (72 . 1)
                       (73 . 2)
                      )
            )                                     ;el atributo cota
            (entmake '((0 . "ATTDEF")
                       (8 . "0")
                       (10 0.5 1.0 0.0)
                       (11 0.5 1.0 0.0)
                       (1 . "")
                       (7 . "STBKCOR")
                       (2 . "ID")
                       (3 . "ID")
                       (40 . 1.2)
                       (41 . 0.8)
                       (50 . 0.0)
                       (70 . 1)
                       (71 . 0)
                       (72 . 1)
                       (73 . 2)
                      )
            )
            (entmake '((0 . "ATTDEF")
                       (8 . "0")
                       (10 0.5 2.0 0.0)
                       (11 0.5 2.0 0.0)
                       (1 . "")
                       (7 . "STBKCOR")
                       (2 . "Muestra")
                       (3 . "Muestra")
                       (40 . 1.2)
                       (41 . 0.8)
                       (50 . 0.0)
                       (70 . 1)
                       (71 . 0)
                       (72 . 1)
                       (73 . 2)
                      )
            )
            (entmake '((0 . "ATTDEF")
                       (8 . "0")
                       (10 0.5 3.0 0.0)
                       (11 0.5 3.0 0.0)
                       (1 . "")
                       (7 . "STBKCOR")
                       (2 . "Fecha")
                       (3 . "Fecha")
                       (40 . 1.2)
                       (41 . 0.8)
                       (50 . 0.0)
                       (70 . 1)
                       (71 . 0)
                       (72 . 1)
                       (73 . 2)
                      )
            )
                (entmake '((0 . "ATTDEF")
                       (8 . "0")
                       (10 0.5 4.0 0.0)
                       (11 0.5 4.0 0.0)    
                       (1 . "")
                       (7 . "STBKCOR")
                       (2 . "Este")
                       (3 . "ESTE")
                       (40 . 0.8)
                       (41 . 0.8)
                       (50 . 0.0)
                       (70 . 1)
                       (71 . 0)
                       (72 . 1)
                       (73 . 2)
                      )
            )
            (entmake '((0 . "ATTDEF")
                       (8 . "0")
                       (10 0.5 5.0 0.0)
                       (1 . "")
                       (7 . "STBKCOR")
                       (2 . "Norte")
                       (3 . "NORTE")
                       (40 . 1.2)
                       (41 . 0.8)
                       (50 . 0.0)
                       (70 . 1)
                       (71 . 0)
                       (72 . 1)
                       (73 . 2)
                      )
            )
            (entmake '((0 . "ATTDEF")
                       (8 . "0")
                       (10 0.5 6.0 0.0)
                       (1 . "")
                       (7 . "STBKCOR")
                       (2 . "Cota")
                       (3 . "COTA")
                       (40 . 1.2)
                       (41 . 0.8)
                       (50 . 0.0)
                       (70 . 1)
                       (71 . 0)
                       (72 . 1)
                       (73 . 2)
                      )
            )
            (entmake '((0 . "ATTDEF")
                       (8 . "0")
                       (10 0.5 7.0 0.0)
                       (11 0.5 7.0 0.0)
                       (1 . "")
                       (7 . "STBKCOR")
                       (2 . "Azimut")
                       (3 . "AZIMUT")
                       (40 . 1.2)
                       (41 . 0.8)
                       (50 . 0.0)
                       (70 . 1)
                       (71 . 0)
                       (72 . 1)
                       (73 . 2)
                      )
            )
            (entmake '((0 . "ATTDEF")
                       (8 . "0")
                       (10 0.5 8.0 0.0)
                       (11 0.5 8.0 0.0)
                       (1 . "")
                       (7 . "STBKCOR")
                       (2 . "Angulo")
                       (3 . "ANG")
                       (40 . 1.2)
                       (41 . 0.8)
                       (50 . 0.0)
                       (70 . 1)
                       (71 . 0)
                       (72 . 1)
                       (73 . 2)
                      )
            )  
            (entmake '((0 . "ATTDEF")
                       (8 . "0")
                       (10 0.5 9.0 0.0)
                       (11 0.5 9.0 0.0)
                       (1 . "")
                       (7 . "STBKCOR")
                       (2 . "Alt.Muestra")
                       (3 . "Alt.M.")
                       (40 . 1.2)
                       (41 . 0.8)
                       (50 . 0.0)
                       (70 . 1)
                       (71 . 0)
                       (72 . 1)
                       (73 . 2)
                      )
            )
            (entmake '((0 . "ATTDEF")
                       (8 . "0")
                       (10 13.00 -0.4 0.0)
                       (11 13.00 -0.4 0.0)
                       (1 . "")
                       (7 . "STBKCOR")
                       (2 . "A.Muestra")
                       (3 . "Am.")
                       (40 . 1.2)
                       (41 . 0.8)
                       (50 . 0.0)
                       (70 . 0)
                       (71 . 0)
                       (72 . 1)
                       (73 . 2)
                      )
            )
            (entmake '((0 . "ATTDEF")
                       (8 . "0")
                       (10 19.00 -0.4 0.0)
                       (11 19.00 -0.4 0.0)
                       (1 . "")
                       (7 . "STBKCOR")
                       (2 . "A.Labor")
                       (3 . "Al.")
                       (40 . 1.2)
                       (41 . 0.8)
                       (50 . 0.0)
                       (70 . 0)
                       (71 . 0)
                       (72 . 1)
                       (73 . 2)
                      )
            )
            (entmake '((0 . "ATTDEF")
                       (8 . "0")
                       (10 25.00 -0.4 0.0)
                       (11 25.00 -0.4 0.0)
                       (1 . "")
                       (7 . "STBKCOR")
                       (2 . "Cobre")
                       (3 . "%Cu")
                       (40 . 1.2)
                       (41 . 0.8)
                       (50 . 0.0)
                       (70 . 0)
                       (71 . 0)
                       (72 . 1)
                       (73 . 2)
                      )
            )
            (entmake '((0 . "ATTDEF")
                       (8 . "0")
                       (10 31.00 -0.4 0.0)
                       (11 31.00 -0.4 0.0)
                       (1 . "")
                       (7 . "STBKCOR")
                       (2 . "Plomo")
                       (3 . "%Pb")
                       (40 . 1.2)
                       (41 . 0.8)
                       (50 . 0.0)
                       (70 . 0)
                       (71 . 0)
                       (72 . 1)
                       (73 . 2)
                      )
            )
            (entmake '((0 . "ATTDEF")
                       (8 . "0")
                       (10 37.00 -0.4 0.0)
                       (11 37.00 -0.4 0.0)
                       (1 . "")
                       (7 . "STBKCOR")
                       (2 . "Zinc")
                       (3 . "%Zn")
                       (40 . 1.2)
                       (41 . 0.8)
                       (50 . 0.0)
                       (70 . 0)
                       (71 . 0)
                       (72 . 1)
                       (73 . 2)
                      )
            )
            (entmake '((0 . "ATTDEF")
                       (8 . "0")
                       (10 43.00 -0.4 0.0)
                       (11 43.00 -0.4 0.0)
                       (1 . "")
                       (7 . "STBKCOR")
                       (2 . "Plata")
                       (3 . "OzAg")
                       (40 . 1.2)
                       (41 . 0.8)
                       (50 . 0.0)
                       (70 . 0)
                       (71 . 0)
                       (72 . 1)
                       (73 . 2)
                      )
            )
            (entmake '((0 . "ATTDEF")
                       (8 . "0")
                       (10 49.00 -0.4 0.0)
                       (11 49.00 -0.4 0.0)
                       (1 . "")
                       (7 . "STBKCOR")
                       (2 . "Oro")
                       (3 . "GrAu")
                       (40 . 1.2)
                       (41 . 0.8)
                       (50 . 0.0)
                       (70 . 1)
                       (71 . 0)
                       (72 . 1)
                       (73 . 2)
                      )
            )
            (entmake '((0 . "ATTDEF")
                       (8 . "0")
                       (10 55.00 -0.4 0.0)
                       (11 55.00 -0.4 0.0)
                       (1 . "")
                       (7 . "STBKCOR")
                       (2 . "Fierro")
                       (3 . "%Fe")
                       (40 . 1.2)
                       (41 . 0.8)
                       (50 . 0.0)
                       (70 . 1)
                       (71 . 0)
                       (72 . 1)
                       (73 . 2)
                      )
            )
            (entmake '((0 . "ATTDEF")
                       (8 . "0")
                       (10 61.00 -0.4 0.0)
                       (11 61.00 -0.4 0.0)
                       (1 . "")
                       (7 . "STBKCOR")
                       (2 . "Arsenico")
                       (3 . "%As")
                       (40 . 1.2)
                       (41 . 0.8)
                       (50 . 0.0)
                       (70 . 1)
                       (71 . 0)
                       (72 . 1)
                       (73 . 2)
                      )
            )
            (entmake '((0 . "ATTDEF")
                       (8 . "0")
                       (10 67.20 -0.4 0.0)
                       (11 67.00 -0.4 0.0)
                       (1 . "")
                       (7 . "STBKCOR")
                       (2 . "Antimonio")
                       (3 . "%Sb")
                       (40 . 1.2)
                       (41 . 0.8)
                       (50 . 0.0)
                       (70 . 1)
                       (71 . 0)
                       (72 . 1)
                       (73 . 2)
                      )
            )
            (entmake '((0 . "ATTDEF")
                       (8 . "0")
                       (10 73.00 -0.4 0.0)
                       (11 73.00 -0.4 0.0)
                       (1 . "")
                       (7 . "STBKCOR")
                       (2 . "Bismuto")
                       (3 . "%Bi")
                       (40 . 1.2)
                       (41 . 0.8)
                       (50 . 0.0)
                       (70 . 1)
                       (71 . 0)
                       (72 . 1)
                       (73 . 2)
                      )
            )
            (entmake '((0 . "ATTDEF")
                       (8 . "0")
                       (10 79.00 -0.4 0.0)
                       (11 79.00 -0.4 0.0)
                       (1 . "")
                       (7 . "STBKCOR")
                       (2 . "Volframio")
                       (3 . "%W")
                       (40 . 1.2)
                       (41 . 0.8)
                       (50 . 0.0)
                       (70 . 1)
                       (71 . 0)
                       (72 . 1)
                       (73 . 2)
                      )
            )
            (entmake '((0 . "ATTDEF")
                       (8 . "0")
                       (10 85.00 -0.4 0.0)
                       (11 85.00 -0.4 0.0)
                       (1 . "")
                       (7 . "STBKCOR")
                       (2 . "Niquel")
                       (3 . "%Ni")
                       (40 . 1.2)
                       (41 . 0.8)
                       (50 . 0.0)
                       (70 . 1)
                       (71 . 0)
                       (72 . 1)
                       (73 . 2)
                      )
            )
            (entmake '((0 . "ATTDEF")
                       (8 . "0")
                       (10 91.00 -0.4 0.0)
                       (11 91.00 -0.4 0.0)
                       (1 . "")
                       (7 . "STBKCOR")
                       (2 . "Cobalto")
                       (3 . "%Co")
                       (40 . 1.2)
                       (41 . 0.8)
                       (50 . 0.0)
                       (70 . 1)
                       (71 . 0)
                       (72 . 1)
                       (73 . 2)
                      )
            )
            (entmake '((0 . "ATTDEF")
                       (8 . "0")
                       (10 97.00 -0.4 0.0)
                       (11 97.00 -0.4 0.0)
                       (1 . "")
                       (7 . "STBKCOR")
                       (2 . "Oxido_Plomo")
                       (3 . "OxPb")
                       (40 . 1.2)
                       (41 . 0.8)
                       (50 . 0.0)
                       (70 . 1)
                       (71 . 0)
                       (72 . 1)
                       (73 . 2)
                      )
            )
            (entmake '((0 . "ATTDEF")
                       (8 . "0")
                       (10 103.00 -0.4 0.0)
                       (11 103.00 -0.4 0.0)
                       (1 . "")
                       (7 . "STBKCOR")
                       (2 . "Oxido_Zinc")
                       (3 . "OxZn")
                       (40 . 1.2)
                       (41 . 0.8)
                       (50 . 0.0)
                       (70 . 1)
                       (71 . 0)
                       (72 . 1)
                       (73 . 2)
                      )
            )
            (entmake '((0 . "ATTDEF")
                       (8 . "0")
                       (10 109.00 -0.4 0.0)
                       (11 109.00 -0.4 0.0)
                       (1 . "")
                       (7 . "STBKCOR")
                       (2 . "Insoluble")
                       (3 . "Ins.")
                       (40 . 1.2)
                       (41 . 0.8)
                       (50 . 0.0)
                       (70 . 1)
                       (71 . 0)
                       (72 . 1)
                       (73 . 2)
                      )
            )
                                   ;final del bloque
            (entmake '((0 . "ENDBLK")))
;;;        )
;;;    )
)
