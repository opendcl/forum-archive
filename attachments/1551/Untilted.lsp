(defun c:go ()
  (command "OPENDCL")
  (dcl_Project_Load "Untitled" T)
  (dcl_Form_Show Untitled_Form1)
  (princ)
)
; TextBox1
(defun c:Untitled_Form1_PictureBox1_OnClicked (/ str)
  (setq str (dcl_Control_GetText Untitled_Form1_TextBox1))
  (or (= str "")
      (progn
	(setq str (if (= (vl-string-position 45 str) 0) (substr str 2) (strcat "-" str)))
	(dcl_Control_SetText Untitled_Form1_TextBox1 str)
  ))
)
(defun c:Untitled_Form1_PictureBox1_OnDblClicked (/ str)
  (setq str (dcl_Control_GetText Untitled_Form1_TextBox1))
  (or (= str "")
      (dcl_Control_SetText Untitled_Form1_TextBox1 ""))
)
; TextBox2
(defun c:Untitled_Form1_PictureBox2_OnClicked (/ str)
  (setq str (dcl_Control_GetText Untitled_Form1_TextBox2))
  (or (= str "")
      (progn
	(setq str (if (= (vl-string-position 45 str) 0) (substr str 2) (strcat "-" str)))
	(dcl_Control_SetText Untitled_Form1_TextBox2 str)
  ))
)
(defun c:Untitled_Form1_PictureBox2_OnDblClicked (/ str)
  (setq str (dcl_Control_GetText Untitled_Form1_TextBox2))
  (or (= str "")
      (dcl_Control_SetText Untitled_Form1_TextBox2 "1"))
)
