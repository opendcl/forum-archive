(if (not (vl-bb-ref 'Drafting))
  (vl-bb-set
    'Drafting
    (dcl_project_import
      '("YWt6A9pBAABBQ8qyBuKTJSMSaitqQDUXRcp1o3x0ONw1vvY0D6WTyCNg8iw2Kt7K2z8zNg6lEzXb"
"yn80V7r6S0/f91qU9bjWkbiG5d5u4WQDv2m93XFA5o483F7CHi+SBLDHTUVNGYAIFsWjWEW1suMN"
"kceZoAWQh5BDiQr2m5mM3qGkEEZ3Z2b8d2b/T2b4VH7GKHUu+VdPErMcH0XMGt597K5yM6540+bt"
"uMkognNeo/oqaHiP2Kxy2s4wZYzKXgFoB4SPmHiNWk/7YieCyx4QdbUXnUq1bHlf/yptjVb3gybo"
"nEW94ordhKtu8/6gLaZ2JHoo/gCvtnBchVr0RvpdZfpN3oN5SwQP+kTdA1yWNz+B9lOWSkPKoTqH"
"Z2VjYf7jXssHehpR8L5/Ugd3kW+YtL5WQLEf5yhtz7WBKcpJWxYzjiH7y7iGCzsWw86sttxPFpmr"
"LpbUWwTTN8E2ihs/ARmsUpEFPyFMl/U6oUmlnYx1onIhJ9zJptgW69/ixkc3QaVGPqUYEV8024sy"
"kO5NwKRurPsc8Z2lQDKFT2N7U1QKKVMKictWgSyuIXeE9X4lZ1NWPK+5egPCTtK2Izr7SFC0oW6K"
"RdzD5fvvVQSwmpn3wFuUgSfmdjsRa4uBTIW9m1DIynxKXbUUOUnWhVV1vSmbebKMeq9LyPckETIu"
"YrhvUpiSuW9snYZKkjyFOKatybzglXpDGBVZxGFb78rdEnrdhsBl4b3egx6IkViLofz9i1qZZ0/g"
"+bIMFC6VSJcX3AUyhDPsifnOnFk6g1DtoDOKIP/VA/ygUZbpe1Mvjdqu9Xs7yhg41wpL7Xf33IQw"
"Kq9G4jzrk/ytRl9KWx1sPzFrxaTHNS3VHlnRA30O8mmEdFhpaO15+rOnTyat9y1L+LSZm88qRtVo"
"xsyeEF2vYfYIUsaVfUWQRPaAtqIhJqDd/JBvRI6/mwjOnQxthp3shcn+xhJ7Y+kvWGPG0k3Om/20"
"E7vcrDMoe+018zdJARZnXq0LOYo/WAX8Q3y3G/KyEMLdGigV5gIwXM3IcetF+1ak+0bkDBxYdl0V"
"NPLvAK+gyt4hb4re3lu4QGiKn2wdDjbKaf63GbsyWcKxNoF2oei6J09iWURSPGV7rGBqz2PcI5e9"
"NLr4ixfJ5UpXMRVsiq3cg+F6U4mgs3wPRbKMp42AVX7xucx8riBnuBmYj7VrXlOEZRw7BmVSf+xo"
"FrmjxGes5sgdqeRGszz0vWfKbdlHPuz/WnlIVlbsv2RXUttON3yx1lcC5H/sWphxXCF4R8xifBe5"
"RBPmpbq/6n+aWPcXAhWbLjdBmFrmBfZ9VrrldHbuqmEadWU6X20CKkD1kVlpRTLMu7U7D5U1p3o1"
"kPc9nANUwVJyVDrO+hfhHrdur4geN6rU3MYLvAI8WNE5gj1YTwnDJXxZdWl2xn9w+bkFMlsOBZD2"
"R/M/xjuMDrrAtgN4gPXmQoaxPMY78pcHxk/p9tC6vzyHaAD/7NaLehNF6mvx5wUbBi7BTbGdvtj2"
"Y1liniS+/YSRzs65f1Bx/92Zv//d2A7l5OmfKjCecfYu8e73EwUnQvpQg1BIccqAdFDQAXbKTMS1"
"ZtOiwQffq7X2VBYDfsqsJzr7Lwg0ytDMhOFdDnSrYmjZPzmL41iDdq+TfOE1ngsge2kCkK8pSt1h"
"PyCWvcQBEY7J9g/KdIcMyTP0i11blPlG5M3pwSmeC2A5jc4GAeuKzwTnBcdMfFkvhOTeHTVl/9Xd"
"WXtQhF/3xc6EzN39vWsngCTd431pE+6YkTlMxiJIDS5a+9myX3AnWsdK/xGKo/ZndDcOhlr7DHgu"
"sF41MhzTcOg2/+xyAV8cAkHsmNE5+OZZsypNqBI5Aw5WOr8a7SIE1AQfcWJ0YYRGWZYCT99wq+ik"
"Q4ieQ7814FSTvOMbSaB9xvQyHkNUdXbW/ojf3lF0BA89WzK1Tv53bnsul+4qO5J+IJYu9EMKzNBp"
"q0a3BbR2EaMPg7Gs2a8YnK75EZ0Kxox32u7lmpkUqIiUYDz4mS8GYmCheGfoHtElbMEc54VvX2L9"
"pbz/mYxkT60fSQAXoTWOKUmYkcglFubBxLP+HR3xV23bkQ5MBqWz7CIelbixjMU6ATVmsNyIgrxN"
"1mV8iye4r2YLoPC3s4Dm6stV1tLebPwvt5ujfBtA1mJ4dnRcSaYvl06VDLraRJxHCbcwoABZp53n"
"dsc1pJUojia/XXqd78FAk2iGjL+dL86dj0MOng/jo27zESjr8UcujlW1bOlzxCx6UBUqmYVuB3Ch"
"i48eoavWJ78a10/HiHuAPr6KqZLZYgM86V8QhwFhCnVi+HY1EXt5ELV0793eXUy42n3vq5gJrRvK"
"9E2BfCZ9tXMfcym+EHMPjsn4b84lfQHRKriovpOn6aO5/OJfvUJU9RCO3DXz73MaRx1r0pLDIIGA"
"xcFKAARjQPnDKQQ4WX6QHKfQgwmLFO0GEX17sWapLGO2/6nrLfvH4jSWOSeG5ufnv+JCgf0CIFuK"
"3VICMgUiWdgqpNaodpO6h0IjJFBhWIMF/ZQN2i83xc4/yD3kZ4qvslOoslNps0omSk3LZuQvfMoi"
"bOGtK5BXLrTpMB3k3g8re9re2eTYsdQYq7auTM9rq7SKCn2xhwoQ6IzuKofHJ+txnusxtxPNxDCk"
"ix/J658b3Gf1w13qoNzrXmhNFh0SR8Fq1U8hUti6ZfYKxTZNOQNKLS075N9ZIxNeL8rvjdHTfrlL"
"nQNndLWHjibmjegBUCt0rIYhoC8pKM90ChOw9QqbyZgFT1JeAU80bQOI1Jyq5jEB4mR1ksLxWPWa"
"yTDVlUKECiwqVzirgPg/NmePPzRlXduze1dPdSzetPdqhOWfoiLA9rW3mCQvGoSqdGom8gIZ2NUC"
"mUVAdWRWIlTZvp4StiS7J6OL9DoKuXQhfOfTY43kaU9olRIEc8eGgLGPm7ses88MBEsk8heHpj13"
"0IF/SvT6Zw=="))))



;;;							;
;;;	Form 01 - Save Window View			;
;;;							;
;;;pgp: kbSaveViewWindow,		*kbSaveViewWindow
(defun c:Drafting_SaveView_OnInitialize (/)
    (dcl_Control_SetTitleBarIcon Drafting_SaveView 100)
    (dcl_Control_SetPicture Drafting_SaveView_SaveButton 100)
    (dcl_Control_SetMouseOverPicture Drafting_SaveView_SaveButton 100)
    )

(defun c:Drafting_SaveView_SaveButton_OnClicked (/ Value)
    (Setq Value (dcl_Control_GetText Drafting_SaveView_TextBox))
    (if	Value
      (progn (dcl_form_close Drafting_SaveView)
	     (command "-view" "_w" Value)
	     (while (= (logand (getvar "CMDACTIVE") 1) 1) (vl-cmdf pause))
	
	     )
      (dcl_messagebox "Enter a View Name to save" "Save View" 2 3)
      )
    )
(defun c:Drafting_SaveView_CloseButton_OnClicked (/)
  (dcl_form_close Drafting_SaveView)
)

(defun c:kbSaveViewWindow (/)
  (if (not (member "Drafting" (dcl_GetProjects)))
    (dcl_Project_load "Drafting")
    )
  (if dcl_HideErrorMsgBox
    (dcl_Form_Show Drafting_SaveView)
    (alert "The OpenDCL arx module did not load!")
    )
  ;(c:kbSaveViewWindow)
  (princ)
  (princ)
  )
