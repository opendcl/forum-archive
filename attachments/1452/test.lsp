(defun c:test ()
  (dcl_project_load "d:/Test.odcl" T) 
  (defun c:Test_Form1_OnInitialize (/)
    (dcl_Grid_AddRow Test_Form1_Grid1 "" "")
    (dcl_Grid_SetCellDropList Test_Form1_Grid1 0 1 (list "A" "B" "C"))
  )
  (dcl_form_show Test_Form1)
)
(c:test)
