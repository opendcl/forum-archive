(defun PALETTE-TEST ()

	(dcl-project-import
		'("YWt6A9QFAACdGFNZBuITLbUUaj9qQ0MYWBtiWnpcnFQeOj84WI00nCyu+zBKQAC+903e50I2PHKn"
		"Guf7kIN7aUBsjn/8ZSnEjX2Cfe32nDRfk8dL49CX/SsqqUMDEKPE0WTwcR1alYZS5Ma5J5zE9MWC"
		"OH7AcHw9e3QqZxGfQNiO/g3wzT0rPWPKVqsumMH0gUmbh2xkgmTU3jDX/1RY1iuQI2flu1RTMOzh"
		"WqXe02ykolWgCHOt6qXq2INSLdSEpSTKqdgqiWRLoO49r8Lbr2ZGfWmPMUxSyBsKz7gnnBQd6yGJ"
		"Z105ZPfUxf1/inPJm02euWG95VZaTsx2osSe8bYZsLm8AWwAWqaBM7cDbYO5/PE7J4GgtYfJnJFF"
		"n6F2gSqSQW3CX8ZuG49IePGSJ5yjpzKsjanO+mtSzpiwt7dRZzPGdSex9Ljgjo7sqEypS/2B1yBw"
		"ULMyIZuAZGDusqF0ArNMLbYiD9TtBkC4KAf2M6FMHcayG+MimMC/K4nDkoxsJS/MyF0jy2XOR58g"
		"9YBVv1F7wW5CWojKtWhNz+PiHxL1ItUmmKXljdEN/K8in/0J8SwlQEEQN4485MmW2SsCIIYQvqDp"
		"cV+xqFSDYwGkjjuPC0qOKDJJZY5RvTFaiKX/SbxjtIN5nKEA5PWgh5Gs+UE8AiABUZOOYGDpjZm8"
		"g7HzwWcOrYSUOL6AAi2O8p6V/Ivj4ukkicPlwxqBeQk5tms=")
	)

	(dcl-form-show "pltt-test" "pltt-test")
)

(defun C:PT () (PALETTE-TEST) )
