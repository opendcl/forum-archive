(defun addsuppath (np / en nen np) ;~;Tool to add a support path by pathname
(setq
	en (strcase (getenv "ACAD"))
	np (strcase np)
	nen (strcat en ";" np)
)
(setenv "ACAD" nen)
(princ)
)
(addsuppath "Z:\\coversheet2")
(command "_OPENDCL")
(setq strings (list "String 1" "String 2" "String 3" "String 4"))
(defun c:cs2 (/)
	(dcl_Project_Load "cover" T)
	(dcl_Form_Show cover_disc_select)
	(princ)
)
(defun c:cover_disc_select_OnInitialize (/)
	(dcl_ListBox_AddList cover_disc_select_disciplines strings)
)
;(dcl_ListBox_AddString cover_disc_select_disciplines "string 1")
;(dcl_ListBox_AddString cover_disc_select_disciplines "string 2")
;(dcl_ListBox_AddString cover_disc_select_disciplines "string 3")
;(dcl_ListBox_AddString cover_disc_select_disciplines "string 4")
