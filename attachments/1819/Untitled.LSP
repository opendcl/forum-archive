(defun C:test ( / )
  (command "OPENDCL")
  (dcl_Project_Load "Untitled.odcl")
  (dcl_Form_Show Untitled_Form1)
  (princ)
  )

(defun c:Untitled_Form1_TextButton1_OnClicked (/)
  (setq cmd (getvar "CMDECHO"))
  (setvar "CMDECHO" 0)
(setvar "ATTREQ" 1)
  (if (setq FILE (getfiled "Example1" "c:/" "" 2))
    (progn (setq FILE (open FILE "r"))
      (while (setq ZEILE (read-line FILE))
	(progn
	  (setq DATA (STD-STRTOK ZEILE " , ")
		PKT (list (atof (caddr DATA)) (atof (cadr DATA)) (atof (cadddr DATA)))
		PNR (car DATA)
		ZKO (rtos (caddr PKT) 2 3)
		PCODE (last DATA))
	  )
	(command "color" 7)
	(command "_.INSERT" "meas" PKT (getvar "dimscale") (getvar "dimscale") 0 PNR ZKO PCODE)

	)
      (close FILE)
      )
    (alert "no file select!")
    )
  )

(defun c:Untitled_Form1_TextButton2_OnClicked (/)
  (vl-load-com)
  (if (and(setq file(getfiled "Example2" "c:/" "" 1))
          (setq file(open file "w"))       
          (setq aws (ssget '((0 . "INSERT"))))
      )                 
    (progn
      (setq i -1
	    z -1)
      (repeat (sslength aws)
	(setq obj (ssname aws (setq i(1+ i))))
	(cond
	  ((= (cdr (assoc 2 (entget obj))) "koordinatpunkt")
	   (setq pnr (cdr (assoc 1 (entget (entnext obj)))))
	   (setq pco (cdr (assoc 10 (entget obj))))
	   (princ (strcat pnr "," (rtos (nth 0 pco) 2 4) "," (rtos (nth 1 pco) 2 4) "," (rtos (nth 2 pco) 2 4) ",US,") file)
	   (princ "\n" file)
	   (setq z (1+ z))
	   )
	  
	  )
	)
      (close file)
      )
    )
  (princ (strcat "\n" (itoa (1+ z))  " Blocks exported"))
  (princ)
  )
