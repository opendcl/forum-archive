;===========================================================================================
(defun StartDcl ( / )

	(command "_OPENDCL")  
	(dcl_Project_Load "CloseOpenControlBar.odcl" T)
	
	;-----------------------------------------------------------------------------------------
	;-----Start Dcl----------------------------------------------------------------------
	;-----------------------------------------------------------------------------------------
	(dcl-Form-Show CloseOpenControlBar/Form1)
)
;-----------------------------------------------------------------------------------------
(defun CloseDcl ()
	(dcl-Form-Close CloseOpenControlBar/Form1)
)
;-----------------------------------------------------------------------------------------
(defun OpenDcl ()
	(dcl-Form-Show CloseOpenControlBar/Form1)
)
;===========================================================================================
