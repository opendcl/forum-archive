;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;                                                                                                                                    ;;
(defun c:xxxxx ( / )
  (defun c:xT/Form1/Cancel#OnClicked ( / )
    (dcl-Form-Close xT/Form1)
    )
  (dcl_Project_Load "D:\\LISP Projects\\blueTOOLS\\OpenDCL\\xT.odcl" T)
  (dcl_Form_Show xT/Form1)
  (princ)
  )
;;;                                                                                                                                    ;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
